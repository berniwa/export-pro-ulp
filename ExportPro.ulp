/**
 * This ULP is black magic
 * This ULP will handle all export/documentation tasks
 * with a view clicks
 *
 * @author 		Bernhard Wörndl-Aichriedler <bwa@xdevelop.at>
 * @author 		Patricia Schöndorfer <ps@xdevelop.at>
 * @author 		Tobias Hofer <thofer@xdevelop.at>
 * @author 		Philipp Doppelhammer <philipp@xdevelop.at>
 * @copyright	2006-2019, Bernhard Wörndl-Aichriedler
 * @license 	BSD-3-Clause
 */

 #usage "<b>Generate and export project documentation and files</b>\n"
       "<author>Bernhard Wörndl-Aichriedler 2006-2019 </author>"

#include "include/Include_Misc.ulp";
#include "include/Include_Dru.ulp";
#include "include/Include_Language.ulp";
#include "include/Include_Config.ulp";
#include "include/Include_CheckExport.ulp";

void debugMsg(string msg){
	//to prevent debug messages to apear in releace
	dlgMessageBox(msg);
}

void debugVal(string msg, int val){
	sprintf(msg,"%s%d",msg,val);
	debugMsg(msg);
}


string include_path = "Include_";


string ULP_VERSION = "ExportPro";
int ULP_REVISION_FORMAT_REVISION = 7;


string cmd = "", bname = "", layers = "", palette_name = "BLACK", config_file = "exportpro.cfg", config_file2 = "-exportpro2.cfg", drc_file = "-exportpro.dru";

char UI_LESS=0;

int 
layout_bot = 1, layout_top = 1, parts_top = 1, parts_bot = 1, drills = 1, measure = 1, drilltable = 1, 
construction = 1, reference = 0, enable_export_png = 1, bom = 1, mirror_bot = 1, crop_all = 1, no_measures = 0, auto_project = 1,
bom_xls = 1, bom_csv = 0, bom_dbase3 = 0, bom_farnell = 0, bom_shorten_names = 1, bom_display_package_type = 1, 
parts_display_names = 1, parts_display_values = 1, pricing = 0, idf_export = 1, pcbimage_top = 1, 
pcbimage_bottom = 1, image_resolution = 2, pcbimage_color = 0,
pcbimage_silkscreen_color = 0, pcbimage_plating = 0,
silkscreen_tplace = 1, silkscreen_tnames = 1, silkscreen_tvalues = 1, silkscreen_tdocu = 1,
silkscreen_bplace = 1, silkscreen_bnames = 1, silkscreen_bvalues = 1, silkscreen_bdocu = 1,
renumber = 1,
output_date_folder = 1, 
schematic_export = 1, schematic_format = 1, schematic_bw = 1, schematic_color = 1, 
layout_inner_layer = 1, 
board_layer[] = {1, 0, 0, 0, 0, 0, 0, 0, 0, 0, 0, 0, 0, 0, 0, 1},
format_revision = 0,
gerber_export = 1, 
gerber_copper = 1, gerber_stc = 1, gerber_sts = 1, gerber_plc = 1, 
gerber_pls = 1, gerber_crc = 1, gerber_crs = 1, gerber_drd = 1, gerber_otl = 1,
gerber_ref = 0, gerber_fab = 1, parts_top_docu = 1, parts_bot_docu = 1,
board_type = 0,
eagle_export = 1, ec_export, gerber_format = 0,
pnp_export = 1, pnp_top = 1, pnp_bot = 1, pnp_flip = 0, pnp_auto_offset = 0,
fabrication = 1, stackup = 1, board_info = 1,
enable_export_pdf = 1, pdf_keep_frame = 1, pdf_merge = 1,
enable_export_image = 1,
bomToPDF = 1,
board_format = 0,
bomPreset=0
;

real board_thickness = 0.0, board_copper_thickness = 0.0,
bom_quantity, pnp_offset_x = 0.0, pnp_offset_y = 0.0,
bom_offsetX = 0.15, bom_offsetY = 0.15, bom_width = 179.6,
temp_min, temp_max, minMeasureDiameter = 2.0
;



real copper_layer_thickness[]={18, 0, 0, 0, 0, 0, 0, 0, 0, 0, 0, 0, 0, 0, 0, 18};

string output_folder = "./docu/";

string board_title 		= "MyProject";
string board_subtitle 	= "Version 1.0";

string output_folder_idf, output_file_img_pcbt, 
output_file_img_pcbb, output_file_pdf_pcbt, output_file_pdf_pcbb,
output_file_schematic_bw, output_file_schematic_color,
output_file_gerber_copper_top,  output_file_gerber_copper_bottom, output_file_gerber_copper_other,
output_file_gerber_st, output_file_gerber_sb,
output_file_gerber_pt, output_file_gerber_pb,
output_file_gerber_ct, output_file_gerber_cb,
output_file_gerber_drill, output_file_gerber_otl,
output_file_gerber_ref, output_file_gerber_fab, 
output_file_gerber_spec, output_folder_eagle, 
output_file_eagle_spec, ecpanel_path
;


string waitingList[];
int waitingcount = 0;


string layer_fill[];

string copper_layer_Name[];

string boardname = "output";

int pcbImageResolutions[]			= {600, 1200, 2400};
string pcbImagePcbColors[] 			= {"0xFF007800", "0xFF660000", "0xFF010101", "0xFFF5F5F5", "0xFFCC6600"};
string pcbImageCopperColors[] 		= {"0xFF00CA00", "0xFF990000", "0xFF111111", "0xFFFFFFFF", "0xFFFF8C1A"};
string pcbImageSilkscreenColors[] 	= {"0xFFFFFFFF", "0xFFFFFF00", "0xFFAA0000", "0xFF000000", "0x00000000"};
string pcbImagePlating[] 			= {"0xFFC0C0C0", "0xFFC0C0C0", "0xFFE4CA41", "0xFFC0C0C0"};

string pcbSpecColor[] = {
	"green",
	"red", 
	"black", 
	"white",
	"polyimid"
};

string pcbSpecSilkscreenColor[] = {
	"white",
	"yellow", 
	"red", 
	"black",
	"none"
};

string pcbSpecPlating[] = {
	"HASL lead free",
	"any lead free",
	"ENIG",
	"Chem Sn"
};

string PcbType[]					= {"FR4", "Roggers", "Aluminium", "Polyamid"};

string ExportSetup[];

string getSystemFilename(string ends_with){
	return filesetext(bname + boardname,ends_with);
}

string getFilename(string basename, string ends_with){
	return filesetext(basename,ends_with);
}

project.board(B){
	bname = filedir(B.name);
	boardname = filesetext(filename(B.name), "");
	
	
	B.layers(L){
		sprintf(layer_fill[L.number], "%d", L.fill);	

		if(L.visible){
			sprintf(layers, layers + " %d", L.number);
		}

		if(L.number<=16){
			copper_layer_Name[L.number-1]=L.name;
		}
	}

	B.elements(E) {
		if (strstr(E.package.name,"FRAME")!=-1){
			real minx=0,maxx=0;
			E.package.wires(W){
				if(minx > u2mm(W.x1)){
					minx = u2mm(W.x1);
				}
				if(minx > u2mm(W.x2)){
					minx = u2mm(W.x2);
				}
				if(maxx < u2mm(W.x1)){
					maxx = u2mm(W.x1);
				}
				if(maxx < u2mm(W.x2)){
					maxx = u2mm(W.x2);
				}
			}
			bom_width=maxx-minx;
		}
	}
}

string filepath = bname;

real convert2mm(string val){
	real mm = strtod(val);

	if(strstr(val,"mic")!=-1)	mm=u2mm(mic2u(mm));
	else if(strstr(val,"mil")!=-1)	mm=u2mm(mil2u(mm));
	else if(strstr(val,"inch")!=-1)	mm=u2mm(inch2u(mm));

	return mm;
}

void loadDRCSettings(){
	string layerSetup=drcGetRule("layerSetup");
	int layer[];
	int layerCount=0;
	for(int i=0;i<strlen(layerSetup);i++){
		if(isdigit(layerSetup[i])){
			//debugVal(""+layerSetup[i]+":", layerCount);

			layer[layerCount]+=strtol(""+layerSetup[i]);

			if(isdigit(layerSetup[i+1])){
				layer[layerCount] *= 10;
			}
			else{
				layer[++layerCount] = 0;
			}
		}
	}
	sort(layerCount, layer);
	for(int j=0, y=0; j<layerCount;j++){
		if(layer[j] != layer[y]){
			layer[++y] = layer[j];
			//debugVal(""+layer[y]+":", y);
		}
	}
	layerCount=++y;

	//debugVal("Layercount:", layerCount);

	string copper[]; 
	strsplit(copper, drcGetRule("mtCopper"), ' ');

	string isolate[]; 
	strsplit(isolate, drcGetRule("mtIsolate"), ' ');

	board_thickness = 0.0;
	board_copper_thickness = 0.0;

	real conFakt=0;
	i=0;	//Yes this works //nope it did not, but I'll fix it
	for (int l=0;l<16;l++) {
		if(l<(layerCount-1)){
			board_thickness += convert2mm(isolate[l]);
		}
		if(l==(layer[i]-1)){
			board_thickness += convert2mm(copper[l]);
			board_layer[l]=1;
			copper_layer_thickness[l]=convert2mm(copper[l])*1000;
			i++;
		}
		else{
			board_layer[l]=0;
			copper_layer_thickness[l]=0;
		}
	}

	board_copper_thickness=strtod(copper[0])*1000;//to get µm
}

void addToWaitinglist(string file){
	file = filesetext(file,".tmp");
	waitingList[waitingcount++] = file;
}

string parseUserSetting(string data){
	return stringTrim(strsub(data,(strchr(data,'=')+1)));
}

void loadUsersettings(){
	string data[];
	if(filesize(getSystemFilename(config_file2))) {
		int lines = fileread(data, getSystemFilename(config_file2));

		string con;
		for(int i=0; i<lines; i++) {
			con = stringTrim(strsub(data[i],0,strchr(data[i],'=')));

			if (con=="layout_bot") {
				layout_bot = strtol(parseUserSetting(data[i]));
			}
			else if (con=="layout_top") {
				layout_top = strtol(parseUserSetting(data[i]));
			}
			else if (con=="parts_top") {
				parts_top = strtol(parseUserSetting(data[i]));
			}
			else if (con=="parts_bot") {
				parts_bot = strtol(parseUserSetting(data[i]));
			}
			else if (con=="drills") {
				drills = strtol(parseUserSetting(data[i]));
			}
			else if (con=="measure") {
				measure = strtol(parseUserSetting(data[i]));
			}
			else if (con=="drilltable") {
				drilltable = strtol(parseUserSetting(data[i]));
			}
			else if (con=="enable_export_png") {
				enable_export_png = strtol(parseUserSetting(data[i]));
			}
			else if (con=="construction") {
				construction = strtol(parseUserSetting(data[i]));
			}
			else if (con=="bom") {
				bom = strtol(parseUserSetting(data[i]));
			}
			else if (con=="mirror_bot") {
				mirror_bot = strtol(parseUserSetting(data[i]));
			}
			else if (con=="crop_all") {
				crop_all = strtol(parseUserSetting(data[i]));
			}
			else if (con=="bom_xls") {
				bom_xls = strtol(parseUserSetting(data[i]));
			}
			else if (con=="bom_csv") {
				bom_csv = strtol(parseUserSetting(data[i]));
			}
			else if (con=="bom_dbase3") {
				bom_dbase3 = strtol(parseUserSetting(data[i]));
			}
			else if (con=="bom_shorten_names") {
				bom_shorten_names = strtol(parseUserSetting(data[i]));
			}
			else if (con=="bom_display_package_type") {
				bom_display_package_type = strtol(parseUserSetting(data[i]));
			}
			else if (con=="no_measures") {
				no_measures = strtol(parseUserSetting(data[i]));
			}
			else if (con=="auto_project") {
				auto_project = strtol(parseUserSetting(data[i]));
			}
			else if (con=="output_folder") {
				output_folder = parseUserSetting(data[i]);
			}
			else if (con=="layout_inner_layer") {
				layout_inner_layer = strtol(parseUserSetting(data[i]));
			}
			else if (con=="parts_display_names") {
				parts_display_names = strtol(parseUserSetting(data[i]));
			}
			else if (con=="parts_display_values") {
				parts_display_values = strtol(parseUserSetting(data[i]));
			}
			else if (con=="pricing") {
				pricing = strtol(parseUserSetting(data[i]));
			}
			else if (con=="idf_export") {
				idf_export = strtol(parseUserSetting(data[i]));
			}
			else if (con=="pcbimage_top") {
				pcbimage_top = strtol(parseUserSetting(data[i]));
			}
			else if (con=="pcbimage_bottom") {
				pcbimage_bottom = strtol(parseUserSetting(data[i]));
			}
			else if (con=="image_resolution") {
				image_resolution = strtol(parseUserSetting(data[i]));
			}
			else if (con=="pcbimage_color") {
				pcbimage_color = strtol(parseUserSetting(data[i]));
			}
			else if (con=="pcbimage_silkscreen_color") {
				pcbimage_silkscreen_color = strtol(parseUserSetting(data[i]));
			}
			else if (con=="pcbimage_plating") {
				pcbimage_plating = strtol(parseUserSetting(data[i]));
			}
			else if (con=="silkscreen_tnames") {
				silkscreen_tnames = strtol(parseUserSetting(data[i]));
			}
			else if (con=="silkscreen_tvalues") {
				silkscreen_tvalues = strtol(parseUserSetting(data[i]));
			}
			else if (con=="silkscreen_tdocu") {
				silkscreen_tdocu = strtol(parseUserSetting(data[i]));
			}
			else if (con=="silkscreen_bnames") {
				silkscreen_bnames = strtol(parseUserSetting(data[i]));
			}
			else if (con=="silkscreen_bvalues") {
				silkscreen_bvalues = strtol(parseUserSetting(data[i]));
			}
			else if (con=="silkscreen_bdocu") {
				silkscreen_bdocu = strtol(parseUserSetting(data[i]));
			}
			else if (con=="bom_farnell") {
				bom_farnell = strtol(parseUserSetting(data[i]));
			}
			else if (con=="bom_quantity") {
				bom_quantity = strtod(parseUserSetting(data[i]));
			}
			else if (con=="renumber") {
				renumber = strtol(parseUserSetting(data[i]));
			}
			else if (con=="output_date_folder") {
				output_date_folder = strtol(parseUserSetting(data[i]));
			}
			else if (con=="schematic_export") {
				schematic_export = strtol(parseUserSetting(data[i]));
			}
			else if (con=="schematic_bw") {
				schematic_bw = strtol(parseUserSetting(data[i]));
			}
			else if (con=="schematic_color") {
				schematic_color = strtol(parseUserSetting(data[i]));
			}
			else if (con=="schematic_format") {
				schematic_format = strtol(parseUserSetting(data[i]));
			}
			else if (con=="silkscreen_tplace") {
				silkscreen_tplace = strtol(parseUserSetting(data[i]));
			}
			else if (con=="silkscreen_bplace") {
				silkscreen_bplace = strtol(parseUserSetting(data[i]));
			}
			else if (con=="format_revision") {
				format_revision = strtol(parseUserSetting(data[i]));
			}
			else if (con=="gerber_export") {
				gerber_export = strtol(parseUserSetting(data[i]));
			}
			else if (con=="gerber_copper") {
				gerber_copper = strtol(parseUserSetting(data[i]));
			}
			else if (con=="gerber_stc") {
				gerber_stc = strtol(parseUserSetting(data[i]));
			}
			else if (con=="gerber_sts") {
				gerber_sts = strtol(parseUserSetting(data[i]));
			}
			else if (con=="gerber_plc") {
				gerber_plc = strtol(parseUserSetting(data[i]));
			}
			else if (con=="gerber_pls") {
				gerber_pls = strtol(parseUserSetting(data[i]));
			}
			else if (con=="gerber_crc") {
				gerber_crc = strtol(parseUserSetting(data[i]));
			}
			else if (con=="gerber_crs") {
				gerber_crs = strtol(parseUserSetting(data[i]));
			}
			else if (con=="gerber_drd") {
				gerber_drd = strtol(parseUserSetting(data[i]));
			}
			else if (con=="board_thickness") {
				board_thickness = strtod(parseUserSetting(data[i]));
			}
			else if (con=="board_type") {
				board_type = strtol(parseUserSetting(data[i]));
			}
			else if (con=="board_copper_thickness") {
				board_copper_thickness = strtod(parseUserSetting(data[i]));
			}
			else if (con=="eagle_export") {
				eagle_export = strtol(parseUserSetting(data[i]));
			}
			else if (con=="gerber_otl") {
				gerber_otl = strtol(parseUserSetting(data[i]));
			}
			else if (con=="reference") {
				reference = strtol(parseUserSetting(data[i]));
			}
			else if (con=="gerber_ref") {
				gerber_ref = strtol(parseUserSetting(data[i]));
			}
			else if (con=="parts_top_docu") {
				parts_top_docu = strtol(parseUserSetting(data[i]));
			}
			else if (con=="parts_bot_docu") {
				parts_bot_docu = strtol(parseUserSetting(data[i]));
			}
			else if (con=="ec_export") {
				ec_export = strtol(parseUserSetting(data[i]));
			}
			else if (con=="gerber_format") {
				gerber_format = strtol(parseUserSetting(data[i]));
			}
			else if (con=="pnp_export") {
				pnp_export = strtol(parseUserSetting(data[i]));
			}
			else if (con=="pnp_top") {
				pnp_top = strtol(parseUserSetting(data[i]));
			}
			else if (con=="pnp_bot") {
				pnp_bot = strtol(parseUserSetting(data[i]));
			}
			else if (con=="pnp_flip") {
				pnp_flip = strtol(parseUserSetting(data[i]));
			}
			else if (con=="pnp_auto_offset") {
				pnp_auto_offset = strtol(parseUserSetting(data[i]));
			}
			else if (con=="pnp_offset_x") {
				pnp_offset_x = strtod(parseUserSetting(data[i]));
			}
			else if (con=="pnp_offset_y") {
				pnp_offset_y = strtod(parseUserSetting(data[i]));
			}
			else if (con=="fabrication") {
				fabrication = strtol(parseUserSetting(data[i]));
			}
			else if (con=="stackup") {
				stackup = strtol(parseUserSetting(data[i]));
			}
			else if (con=="gerber_fab") {
				gerber_fab = strtol(parseUserSetting(data[i]));
			}
			else if (con=="enable_export_pdf") {
				enable_export_pdf = strtol(parseUserSetting(data[i]));
			}
			else if (con=="pdf_keep_frame") {
				pdf_keep_frame = strtol(parseUserSetting(data[i]));
			}
			else if (con=="pdf_merge") {
				pdf_merge = strtol(parseUserSetting(data[i]));
			}
			else if (con=="enable_export_image") {
				enable_export_image = strtol(parseUserSetting(data[i]));
			}
			else if (con=="bomToPDF") {
				bomToPDF = strtol(parseUserSetting(data[i]));
			}
			else if (con=="board_format") {
				board_format = strtol(parseUserSetting(data[i]));
			}
			else if (con=="bom_offsetX") {
				bom_offsetX = strtod(parseUserSetting(data[i]));
			}
			else if (con=="bom_offsetY") {
				bom_offsetY = strtod(parseUserSetting(data[i]));
			}
			else if (con=="bom_width") {
				bom_width = strtod(parseUserSetting(data[i]));
			}
			else if (con=="board_info") {
				board_info = strtol(parseUserSetting(data[i]));
			}
			else if (con=="board_title") {
				board_title = parseUserSetting(data[i]);				
			}
			else if (con=="board_subtitle") {
				board_subtitle = parseUserSetting(data[i]);				
			}
			else if (con=="minMeasureDiameter") {
				minMeasureDiameter = strtod(parseUserSetting(data[i]));				
			}
			else if (con=="cfg_enableAsync") {
				cfg_enableAsync = strtol(parseUserSetting(data[i]));
			}
			else {
				for(int l=0; l<16;l++){
					string s;
					sprintf(s,"%d",l);
					if (con=="board_layer.Nr."+s) {
						board_layer[l] = strtol(parseUserSetting(data[i]));
					}
					else if (con=="copper_layer_thickness.Nr."+s){
						copper_layer_thickness[l] = strtod(parseUserSetting(data[i]));
					}
				}
			}
		}
	}
	else if(filesize(getSystemFilename("-"+config_file))){
		int lines = fileread(data, getSystemFilename("-"+config_file));
		layout_bot = strtol(data[0]);
		layout_top = strtol(data[1]);
		parts_top = strtol(data[2]);
		parts_bot = strtol(data[3]);
		drills = strtol(data[4]);
		measure = strtol(data[5]);
		drilltable = strtol(data[6]);
		enable_export_png = strtol(data[7]);
		construction = strtol(data[8]);
		bom = strtol(data[9]);
		mirror_bot = strtol(data[10]);
		crop_all = strtol(data[11]);
		bom_xls = strtol(data[12]);
		bom_csv = strtol(data[14]);
		bom_dbase3 = strtol(data[15]);
		bom_shorten_names = strtol(data[16]);	
		bom_display_package_type = strtol(data[17]);
		no_measures = strtol(data[18]);
		auto_project = strtol(data[19]);
		output_folder = data[20];
		layout_inner_layer = strtol(data[21]);
		// = strtol(data[22]); //Removed in version 7
		parts_display_names = strtol(data[23]);
		parts_display_values = strtol(data[24]);
		pricing = strtol(data[25]);
		idf_export = strtol(data[26]);
		pcbimage_top = strtol(data[27]);
		pcbimage_bottom = strtol(data[28]);
		image_resolution = strtol(data[29]);
		pcbimage_color = strtol(data[32]);
		pcbimage_silkscreen_color = strtol(data[33]);
		pcbimage_plating = strtol(data[34]);
		silkscreen_tnames = strtol(data[36]);
		silkscreen_tvalues = strtol(data[37]);
		silkscreen_tdocu = strtol(data[38]);
		silkscreen_bnames = strtol(data[40]);
		silkscreen_bvalues = strtol(data[41]);
		silkscreen_bdocu = strtol(data[42]);
		bom_farnell = strtol(data[45]);
		bom_quantity = strtod(data[46]);
		renumber = strtol(data[47]);
		output_date_folder = strtol(data[48]);
		schematic_export = strtol(data[49]);
		schematic_bw = strtol(data[50]);
		schematic_color = strtol(data[51]);
		schematic_format = strtol(data[52]);
		silkscreen_tplace = strtol(data[53]);
		silkscreen_bplace = strtol(data[54]);
		board_layer[0] = strtol(data[55]);
		board_layer[1] = strtol(data[56]);
		board_layer[2] = strtol(data[57]);
		board_layer[3] = strtol(data[58]);
		board_layer[4] = strtol(data[59]);
		board_layer[5] = strtol(data[60]);
		board_layer[6] = strtol(data[61]);
		board_layer[7] = strtol(data[62]);
		board_layer[8] = strtol(data[63]);
		board_layer[9] = strtol(data[64]);
		board_layer[10] = strtol(data[65]);
		board_layer[11] = strtol(data[66]);
		board_layer[12] = strtol(data[67]);
		board_layer[13] = strtol(data[68]);
		board_layer[14] = strtol(data[69]);
		board_layer[15] = strtol(data[70]);		
		format_revision = strtol(data[71]);	

		gerber_export 	= strtol(data[72]);
		gerber_copper 	= strtol(data[73]);
		gerber_stc 	= strtol(data[74]);
		gerber_sts 	= strtol(data[75]);
		gerber_plc 	= strtol(data[76]);
		gerber_pls 	= strtol(data[77]);
		gerber_crc 	= strtol(data[78]);
		gerber_crs 	= strtol(data[79]);
		gerber_drd 	= strtol(data[80]);

		board_thickness 	= strtod(data[81]);
		board_type		= strtol(data[82]);
		board_copper_thickness= strtod(data[83]);

		eagle_export 	= strtol(data[84]);
		
		gerber_otl 	= strtol(data[85]);

		reference = strtol(data[86]);
		gerber_ref  = strtol(data[87]);
		
		parts_top_docu  = strtol(data[88]);
		parts_bot_docu  = strtol(data[89]);
		
		ec_export 		= strtol(data[90]);
		
		gerber_format 	= strtol(data[91]);

		pnp_export		= strtol(data[92]);
		pnp_top			= strtol(data[93]);
		pnp_bot			= strtol(data[94]);
		pnp_flip		= strtol(data[95]);
		pnp_auto_offset = strtol(data[96]);
		pnp_offset_x	= strtod(data[97]);
		pnp_offset_y	= strtod(data[98]);

		fabrication		= strtol(data[99]);
		stackup			= strtol(data[100]);
		gerber_fab		= strtol(data[101]);

		enable_export_pdf = strtol(data[102]);
		pdf_keep_frame	= strtol(data[103]);
		pdf_merge 		= strtol(data[104]);

		if(format_revision == 0)	
		//If the format revision was not set, the version is < 7
		{
			//So we assume a 2 layer or 4 layer PCB
			board_layer[0] = layout_top;
			board_layer[1] = strtol(data[21]);
			board_layer[2] = strtol(data[22]);
			board_layer[15] = layout_bot;
			silkscreen_tplace = 1;
			silkscreen_bplace = 1;
		}
	}
}

void saveUsersettings(){
	output(getSystemFilename(config_file2)){
		printf("layout_bot = %d\n", layout_bot);
		printf("layout_top = %d\n", layout_top);
		printf("parts_top = %d\n", parts_top);
		printf("parts_bot = %d\n", parts_bot);
		printf("drills = %d\n", drills);
		printf("measure = %d\n", measure);
		printf("drilltable = %d\n", drilltable);
		printf("enable_export_png = %d\n", enable_export_png);
		printf("construction = %d\n", construction);
		printf("bom = %d\n", bom);
		printf("mirror_bot = %d\n", mirror_bot);
		printf("crop_all = %d\n", crop_all);
		printf("bom_xls = %d\n", bom_xls);
		printf("bom_csv = %d\n", bom_csv);
		printf("bom_dbase3 = %d\n", bom_dbase3);
		printf("bom_shorten_names = %d\n", bom_shorten_names);
		printf("bom_display_package_type = %d\n", bom_display_package_type);
		printf("no_measures = %d\n", no_measures);
		printf("auto_project = %d\n", auto_project);
		printf("output_folder = %s\n", output_folder);
		printf("layout_inner_layer = %d\n", layout_inner_layer);
		printf("parts_display_names = %d\n", parts_display_names);
		printf("parts_display_values = %d\n", parts_display_values);
		printf("pricing = %d\n", pricing);
		printf("idf_export = %d\n", idf_export);

		printf("pcbimage_top = %d\n", pcbimage_top);
		printf("pcbimage_bottom = %d\n", pcbimage_bottom);
		printf("image_resolution = %d\n", image_resolution);
		printf("pcbimage_color = %d\n", pcbimage_color);
		printf("pcbimage_silkscreen_color = %d\n", pcbimage_silkscreen_color);
		printf("pcbimage_plating = %d\n", pcbimage_plating);

		printf("silkscreen_tnames = %d\n", silkscreen_tnames);
		printf("silkscreen_tvalues = %d\n", silkscreen_tvalues);
		printf("silkscreen_tdocu = %d\n", silkscreen_tdocu);
		printf("silkscreen_bnames = %d\n", silkscreen_bnames);
		printf("silkscreen_bvalues = %d\n", silkscreen_bvalues);
		printf("silkscreen_bdocu = %d\n", silkscreen_bdocu);

		printf("bom_farnell = %d\n", bom_farnell);
		printf("bom_quantity = %f\n", bom_quantity);
		
		printf("renumber = %d\n", renumber);
		printf("output_date_folder = %d\n", output_date_folder);
		printf("schematic_export = %d\n", schematic_export);
		printf("schematic_bw = %d\n", schematic_bw);
		printf("schematic_color = %d\n", schematic_color);
		printf("schematic_format = %d\n", schematic_format);

		printf("silkscreen_tplace = %d\n", silkscreen_tplace);
		printf("silkscreen_bplace = %d\n", silkscreen_bplace);

		for(int l=0; l<16;l++){
			printf("board_layer.Nr.%d = %d\n", l, board_layer[l]);
		}

		printf("ULP_REVISION_FORMAT_REVISION = %d\n", ULP_REVISION_FORMAT_REVISION);	
		
		printf("gerber_export = %d\n", gerber_export);
		printf("gerber_copper = %d\n", gerber_copper);
		printf("gerber_stc = %d\n", gerber_stc);
		printf("gerber_sts = %d\n", gerber_sts);
		printf("gerber_plc = %d\n", gerber_plc);
		printf("gerber_pls = %d\n", gerber_pls);
		printf("gerber_crc = %d\n", gerber_crc);
		printf("gerber_crs = %d\n", gerber_crs);
		printf("gerber_drd = %d\n", gerber_drd);

		printf("board_thickness = %f\n", board_thickness);
		printf("board_type = %d\n", board_type);
		printf("board_copper_thickness = %f\n", board_copper_thickness);

		printf("eagle_export = %d\n", eagle_export);
		
		printf("gerber_otl = %d\n", gerber_otl);

		printf("reference = %d\n", reference);
		printf("gerber_ref = %d\n", gerber_ref);
		
		printf("parts_top_docu = %d\n", parts_top_docu);
		printf("parts_bot_docu = %d\n", parts_bot_docu);

		printf("ec_export = %d\n", ec_export);
		printf("gerber_format = %d\n", gerber_format);

		printf("pnp_export = %d\n", pnp_export);
		printf("pnp_top = %d\n", pnp_top);
		printf("pnp_bot = %d\n", pnp_bot);
		printf("pnp_flip = %d\n", pnp_flip);
		printf("pnp_auto_offset = %d\n", pnp_auto_offset);
		printf("pnp_offset_x = %f\n", pnp_offset_x);
		printf("pnp_offset_y = %f\n", pnp_offset_y);

		printf("fabrication = %d\n", fabrication);
		printf("stackup = %d\n", stackup);
		printf("gerber_fab = %d\n", gerber_fab);

		printf("enable_export_pdf = %d\n", enable_export_pdf);
		printf("pdf_keep_frame = %d\n", pdf_keep_frame);
		printf("pdf_merge = %d\n", pdf_merge);
		printf("enable_export_image = %d\n", enable_export_image);

		for(int i=0;i<16;i++){
			printf("copper_layer_thickness.Nr.%d = %f\n",i,copper_layer_thickness[i]);
		}

		printf("bom_to_pdf = %d\n", bomToPDF);
		printf("board_format = %d\n", board_format);
		printf("bom_offsetX = %f\n", bom_offsetX);
		printf("bom_offsetY = %f\n", bom_offsetY);
		printf("bom_width = %f\n", bom_width);
		printf("board_info = %d\n", board_info);
		printf("board_title  = %s\n", board_title);
		printf("board_subtitle  = %s\n", board_subtitle);
		printf("minMeasureDiameter = %f\n", minMeasureDiameter);
		printf("cfg_enableAsync = %d\n", cfg_enableAsync);
	}
}

string setLayerFill(){
	string cmd = "";
	for(int i = 1; i < 52;i++){
		sprintf(cmd, "%sSET FILL_LAYER %d SOLID;", cmd, i);
	}
	return cmd;
}

string restoreLayerFill(){
	string cmd = "";
	for(int i = 1; i < 52;i++){
		if(layer_fill[i]){
			sprintf(cmd, "%sSET FILL_LAYER %d %s;", cmd, i, layer_fill[i]);
		}
	}
	return cmd;	
}

int exportSetupLookup(string index){
	for(int i = 0; ; i++){
		string fields[];
		int count = strsplit(fields, ExportSetup[i], ';');
		if(count < 3){break;}

		if(stringCompare(fields[0], index) == 0){
			return i;
		}
	}
	return -1;
}

string updateFrameInformationSch(){
	string name[];
	int she[]; //sheet is a reserved name
	string attributes[];
	string attribute;
	string schname;

	char numNames = 0;

	project.schematic(S) {
		schname=filename(S.name);
		S.sheets(ST){
			ST.parts(P) {
				if(strstr(P.device.library, "frame") != -1){
					name[numNames] = P.name;
					she[numNames] = ST.number;
					numNames++;
					int i=0;
					P.attributes(A) {
						attributes[i]=A.name;
						i++;
					}
					attribute = strjoin(attributes,';');
				}
			}
		}
	}

	string cmd = "EDIT .sch;\n";

	for(int j=0; j<numNames; j++) {


		sprintf(cmd,"%sEDIT .s%d;\n",cmd,she[j]);

		//cmd += "CHANGE DISPLAY OFF;\n";

	 	/*
		if(strstr(attribute,"TITLE")==-1) {
			cmd += "ATTRIBUTE " + name[j] + " TITLE DELETE;\n";
		}
		if(strstr(attribute,"SUBTITLE")==-1) {
			cmd += "ATTRIBUTE " + name[j] + " SUBTITLE DELETE;\n";
		}
	 	if(strstr(attribute,"DRAWING")!=-1) {
			cmd += "ATTRIBUTE " + name[j] + " DRAWING DELETE;\n";
		}
		if(strstr(attribute,"EDIT_DATE")!=-1) {
			cmd += "ATTRIBUTE " + name[j] + " EDIT_DATE DELETE;";
		}
		if(strstr(attribute,"FILENAME")!=-1) {
			cmd += "ATTRIBUTE " + name[j] + " FILENAME DELETE;\n";
		}
		if(strstr(attribute,"USERNAME")!=-1) {
			cmd += "ATTRIBUTE " + name[j] + " USERNAME DELETE;\n";
		}
		*/

		
	 	int t = time();
	 	if(UI_LESS){
	 		t=0;
	 	}

	 	sprintf(cmd, "%sATTRIBUTE %s EDIT_DATE \'%s\'; ", cmd, name[j], t2string(t, "dd.MM.yy"));
	 	sprintf(cmd, "%sATTRIBUTE %s DRAWING \'Schematic\';\n", cmd, name[j]);
	 	sprintf(cmd, "%sATTRIBUTE %s FILENAME \'%s\';\n", cmd, name[j], schname);
	 	sprintf(cmd, "%sATTRIBUTE %s USERNAME \'%s\';\n", cmd, name[j], cfg_userName);
	 	sprintf(cmd, "%sATTRIBUTE %s TITLE \'%s\';\n", cmd, name[j], board_title);
	 	sprintf(cmd, "%sATTRIBUTE %s SUBTITLE \'%s\';\n", cmd, name[j], board_subtitle);

		if (schematic_format){
			if(strstr(attribute,"OBJECT_NO")==-1) {
				cmd += "ATTRIBUTE " + name[j] + " OBJECT_NO '';";
			}
			if(strstr(attribute,"CREATE_DATE")==-1) {
				cmd += "ATTRIBUTE " + name[j] + " CREATE_DATE '';";
			}
		}
		else {	//shortname is only present in the A4 frame
	 		sprintf(cmd, "%sATTRIBUTE %s SHORTNAME \'%s\'; ", cmd, name[j], cfg_shortUserName);
		}

	 	if(EAGLE_VERSION>=9){
	 		cmd += "REPOSITION " + name[j] + ";\n\n";
	 	}
	}

	return cmd;
}

string updateFrameInformationBrd(string drawing){
	string name = "";
	string attributes[];
	string attribute;

	board(B) {
		B.elements(E) {
			if(stringCompare(E.package.name, "FRAME") == 0){
				name = E.name;
				int i=0;
				E.attributes(A) {
					attributes[i]=A.name;
					i++;
				}
				attribute = strjoin(attributes,';');
			}
		}
	 }

	string cmd = "";
	if(name != "") {

		//cmd += "CHANGE DISPLAY OFF;";
	 	
	 	/*
		if(strstr(attribute,"TITLE")==-1) {
			cmd += "ATTRIBUTE " + name + " TITLE DELETE;";
		}
		if(strstr(attribute,"SUBTITLE")==-1) {
			cmd += "ATTRIBUTE " + name + " SUBTITLE DELETE;";
		}
	 	if(strstr(attribute,"DRAWING")!=-1) {
			cmd += "ATTRIBUTE " + name + " DRAWING DELETE;";
		}
		if(strstr(attribute,"LAST_EDIT")!=-1) {
			cmd += "ATTRIBUTE " + name + " LAST_EDIT DELETE;";
		}
		if(strstr(attribute,"FILENAME")!=-1) {
			cmd += "ATTRIBUTE " + name + " FILENAME DELETE;";
		}
		if(strstr(attribute,"USERNAME")!=-1) {
			cmd += "ATTRIBUTE " + name + " USERNAME DELETE;";
		}
		if(strstr(attribute,"SHORTNAME")!=-1) {
			cmd += "ATTRIBUTE " + name + " SHORTNAME DELETE;";
		}
		*/


	 	int t = time();
	 	if(UI_LESS){
	 		t=0;
	 	}
	 	sprintf(cmd, "%sATTRIBUTE %s LAST_EDIT \'%s\'; ", cmd, name, t2string(t, "dd.MM.yy"));
	 	sprintf(cmd, "%sATTRIBUTE %s DRAWING \'%s\'; ", cmd, name, stringTrim(drawing));
	 	sprintf(cmd, "%sATTRIBUTE %s FILENAME \'%s.brd\'; ", cmd, name, boardname);
	 	sprintf(cmd, "%sATTRIBUTE %s USERNAME \'%s\'; ", cmd, name, cfg_userName);
	 	sprintf(cmd, "%sATTRIBUTE %s SHORTNAME \'%s\'; ", cmd, name, cfg_shortUserName);
	 	sprintf(cmd, "%sATTRIBUTE %s TITLE \'%s\'; ", cmd, name, board_title);
	 	sprintf(cmd, "%sATTRIBUTE %s SUBTITLE \'%s\'; ", cmd, name, board_subtitle);

		if (board_format){
			if(strstr(attribute,"OBJECT_NO")==-1) {
				cmd += "ATTRIBUTE " + name + " OBJECT_NO '';";
			}
			if(strstr(attribute,"CREATE_DATE")==-1) {
				cmd += "ATTRIBUTE " + name + " CREATE_DATE '';";
			}
		}
		else { //shortname is only present in the A4 frame
	 		sprintf(cmd, "%sATTRIBUTE %s SHORTNAME \'%s\'; ", cmd, name, cfg_shortUserName);
		}

	 	if(EAGLE_VERSION>=9){
	 		cmd += "REPOSITION " + name + "; ";
	 	}
	 }

	return cmd;
}

string exportSetup(string index) {
	int i = exportSetupLookup(index);
	if(i == -1){
		dlgMessageBox(":Unable to find index " + index);
		return "";
	}

	string fields[];
	int count = strsplit(fields, ExportSetup[i], ';');

	string cmd = "";
	cmd += updateFrameInformationBrd(fields[5]);
	cmd += 	"DISPLAY NONE; "+
			"DISPLAY " + fields[2] + "; ";

	return cmd;		
} 

string pngExport(string folder, string index){
	int i = exportSetupLookup(index);
	if(i == -1){
		dlgMessageBox(":Unable to find index " + index);
		return "";
	}

	string fields[];
	int count = strsplit(fields, ExportSetup[i], ';');

	
	string tmp;
	sprintf(tmp,"%d",pcbImageResolutions[image_resolution]);
	string cmd =	"DISPLAY NONE; "+
					"DISPLAY " + fields[2] + "; " + 
					"DISPLAY " + fields[3] + "; " +
					"RUN " + include_path + "ZoomVisible.ulp; " + 
					"SET CONFIRM YES; " + 
					"EXPORT IMAGE '" + folder + stringTrim(fields[1]) + ".png' " + (exp_window?"WINDOW":"") + " MONOCHROME " + tmp + ";";	

	//to mirror the png within eagle
	if(mirror_bot && (strchr(fields[6],'1')!=-1)){
		cmd = "WINDOW FLIP;" + cmd + "WINDOW FLIP;";
	}

	return cmd;	
}

string pngCrop(string folder, string index){
	int i = exportSetupLookup(index);
	if(i == -1){
		dlgMessageBox(":Unable to find index " + index);
		return "";
	}
	
	string fields[];
	int count = strsplit(fields, ExportSetup[i], ';');
	addToWaitinglist(folder + stringTrim(fields[1]));
	return "RUN '"  + include_path + "Crop.ulp' '" + folder + stringTrim(fields[1]) + ".png' '"+getSystemFilename(".bat")+"' " + (cfg_enableAsync?"1":"0") + ";";
}

string pdfExport(string folder, string index){
	int i = exportSetupLookup(index);
	if(i == -1){
		dlgMessageBox(":Unable to find index " + index);
		return "";
	}

	string fields[];
	int count = strsplit(fields, ExportSetup[i], ';');
	string cmd = "" ;
	cmd += 	"DISPLAY NONE; ";
	cmd +=	"DISPLAY " + fields[2] + "; ";
	cmd +=	"DISPLAY " + fields[4] + "; ";

	cmd +=	"PRINT SHEETS ALL -CAPTION HIERARCHY PAPER ";
	cmd +=	(board_format?"A3 landscape":"A4 portrait");
	cmd +=	((fields[6]=="1") && mirror_bot)?" MIRROR":" -MIRROR";
	cmd +=	" BLACK FILE '" + folder + stringTrim(fields[1]) + ".pdf';";

	if ((fields[6]=="1") && mirror_bot && pdf_keep_frame) {
		cmd  = "RUN " + include_path + "MirrorPDF.ulp;" + cmd;
		cmd += "RUN " + include_path + "MirrorPDF.ulp;";
	}

	return cmd;
} //HERE

string exportLayer(int export_layer, int export_png, int export_pdf, string folder_png, string folder_pdf, string index) {
	string cmd = "";
	if(export_layer && (export_png || export_pdf)){
		cmd += exportSetup(index);
		if(export_png) {cmd += pngExport(folder_png, index);}
		if(export_pdf) {cmd += pdfExport(folder_pdf, index);}
	}
	return cmd;
}

void getMinMaxTemp(){
	char initmaxi = 0, initmini = 0;

	project.board(B){
		B.elements(E){
			E.attributes(A){
				if(A.name == "MAX_TEMP"){
					if(!initmaxi){
						temp_max=strtod(A.value);
						initmaxi=1;
					}
					else if(temp_max<strtod(A.value)){
						temp_max=strtod(A.value);
					}
				}
				else if(A.name == "MIN_TEMP"){
					if(!initmini){
						temp_min=strtod(A.value);
						initmini=1;
					}
					else if(temp_min>strtod(A.value)){
						temp_min=strtod(A.value);
					}
				}
			}
		}
	}
}

string resetVew(){
	string cmd = "";

	//reseting visible layers & reset their colors
	cmd += "DISPLAY";
	string cm2 = "";
	project.board(B){
		B.layers(L){
			cmd += " " + (L.visible)?"":"-" + stringFromInt(L.number);
			cm2 += "SET COLOR_LAYER " + stringFromInt(L.number) + " " + stringFromInt(L.color) + ";";
		}
	}
	cmd += ";" + cm2;


	//reseting palette colors (3 palette X 128 entrys)
	for(int i=0; i<PALETTE_TYPES; i++){
		cmd += "SET PALETTE ";
		if(i == PALETTE_BLACK)		{ cmd += "BLACK"; 	}
		else if(i == PALETTE_WHITE)	{ cmd += "WHITE"; 	}
		else						{ cmd += "COLORED"; }
		cmd += ";";

		for(int l=0; l<PALETTE_ENTRIES; l++){
			if(i==PALETTE_WHITE && l==0){	//palett white 0 cant be changed
				continue;
			}

			sprintf(cmd,"%sSET PALETTE %d %s;", cmd, l, cfgget("EAGLE:Palette."+stringFromInt(i)+"."+stringFromInt(l)));
		}
	}

	//reseting visibel palette
	cmd += "SET PALETTE " + palette_name + ";";

	return cmd;
}

void export(){

	if(EAGLE_VERSION>=9){
		cmd+="SET Option.SignalNamesOnTraces 0;";
		cmd+="SET Option.SignalNamesOnPads 0;";
		cmd+="SET Option.LiveDrc 0;";
	}
	else{
		cmd+="SET Option.SignalNames 0;";
	}
	cmd+="SET Option.PadNames 0;";
	cmd+="SET Option.ViaLength 0;";
	cmd+="SET Option.DisplayMode 1;";
	cmd+="SET Option.PolygonRatsnest 1;\n";

	//Save old palette settings
	if(palette(-1) == PALETTE_BLACK)		{ palette_name = "BLACK"; 	}
	else if(palette(-1) == PALETTE_WHITE)	{ palette_name = "WHITE"; 	}
	else									{ palette_name = "COLORED"; }

	output(getSystemFilename(".bat"), "wt"){
		printf("ECHO OFF\n");
		printf("ECHO Finishing export...\n");
	}

	string tsilcsreenLayer =" ";
	tsilcsreenLayer += silkscreen_tplace?"21 ":"";
	tsilcsreenLayer += silkscreen_tnames?"25 ":"";
	tsilcsreenLayer += silkscreen_tvalues?"27 ":"";
	tsilcsreenLayer += silkscreen_tdocu?"51":"";
	string bsilcsreenLayer =" ";
	bsilcsreenLayer += silkscreen_bplace?"22 ":"";
	bsilcsreenLayer += silkscreen_bnames?"26 ":"";
	bsilcsreenLayer += silkscreen_bvalues?"28 ":"";
	bsilcsreenLayer += silkscreen_bdocu?"52":"";

	string preCMD="";
	if(strstr(OS_SIGNATURE,"Windows")>=0){
		preCMD="CMD.EXE /C ";
	}
	else if(strstr(OS_SIGNATURE,"Linux")>=0){
		system("chmod +x \""+getSystemFilename(".bat")+"\"");
	}

	if(filesize(filepath +"fabrication.lbr")>0){
		cmd+="SET CONFIRM YES;";
		cmd+="REMOVE \'"+filepath +"fabrication.lbr\';";
	}

	if(strstr(output_folder, "./") == 0){
		output_folder = bname + strsub(output_folder, 2);
	}

	if(output_folder[strlen(output_folder)] != '/'){
		output_folder += "/";
	}

	string tmp[];

	if(fileglob(tmp, output_folder) == 0) { //Empty folder - ulp never run before
		system(preCMD + "mkdir \"" + output_folder + "\""); //Make new folder
	}

	string image_folder = "", pdf_folder = "", gerber_folder = "", eagle_folder = "", cad_folder = "", ecpanel_folder = "", pnp_folder = "";

	if(output_date_folder) {	//If a date folder and subfolders should be created
		string date_folder 	= t2string(time(), "yyyy-MM-dd") + "/";
		image_folder 		= "images";
		pdf_folder 			= "pdf";
		gerber_folder 		= "gerber";
		eagle_folder 		= "eagle";
		cad_folder 			= "cad";
		ecpanel_folder		= "panel";
		pnp_folder			= "assembly";
		
		output_folder = output_folder + date_folder;

		if(fileglob(tmp, output_folder) <= 0){
			system(preCMD + "mkdir \"" + output_folder + "\""); //Make new folder
		}
		if(enable_export_png == 1 && fileglob(tmp, output_folder + image_folder) <= 0){
			system(preCMD + "mkdir \"" + output_folder + image_folder + "\""); 
		}
		if(gerber_export == 1 && fileglob(tmp, output_folder + gerber_folder) <= 0)	{
			system(preCMD + "mkdir \"" + output_folder + gerber_folder + "\""); 
		}
		if(eagle_export == 1 && fileglob(tmp, output_folder + eagle_folder) <= 0) {
			system(preCMD + "mkdir \"" + output_folder + eagle_folder + "\""); 
		}
		if(idf_export == 1 && fileglob(tmp, output_folder + cad_folder) <= 0) {
			system(preCMD + "mkdir \"" + output_folder + cad_folder + "\""); 
		}
		if(ec_export == 1 && fileglob(tmp, output_folder + ecpanel_folder) <= 0) {
			system(preCMD + "mkdir \"" + output_folder + ecpanel_folder + "\"");
		}
		if(pnp_export == 1 && fileglob(tmp, output_folder + pnp_folder) <= 0) {
			system(preCMD + "mkdir \"" + output_folder + pnp_folder + "\"");
		}
		if(enable_export_pdf == 1 && fileglob(tmp, output_folder + pdf_folder) <= 0) {
			system(preCMD + "mkdir \"" + output_folder + pdf_folder + "\"");
		}

		image_folder 		+= "/";
		pdf_folder	 		+= "/";
		gerber_folder 		+= "/";
		eagle_folder 		+= "/";
		cad_folder 			+= "/";
		ecpanel_folder		+= "/";
		pnp_folder			+= "/";
	}

	string output_file_extension = "";
	
	//Output files to image directory
	string output_folder_image 	= output_folder + image_folder + getFilename(boardname, "");
	string output_folder_pdf    = output_folder + pdf_folder   + getFilename(boardname, "");

	//Replace this with the new config style?
	output_file_img_pcbt = getFilename(output_folder_image, "-pcb-top.png");
	output_file_img_pcbb = getFilename(output_folder_image, "-pcb-bot.png");
	output_file_pdf_pcbt = getFilename(output_folder_pdf, "-pcb-top.pdf");
	output_file_pdf_pcbb = getFilename(output_folder_pdf, "-pcb-bot.pdf");

	string output_file = output_folder + gerber_folder + boardname;
	if(gerber_format == 0){				//Standard EAGLE file naming
		//Output files to gerber directory
		output_file_gerber_copper_top 		= getFilename(output_file, ".cmp");
		output_file_gerber_copper_other 	= getFilename(output_file, ".g");
		output_file_gerber_copper_bottom 	= getFilename(output_file, ".sol");
		output_file_gerber_st				= getFilename(output_file, ".stc");
		output_file_gerber_sb				= getFilename(output_file, ".sts");
		output_file_gerber_pt				= getFilename(output_file, ".plc");
		output_file_gerber_pb				= getFilename(output_file, ".pls");
		output_file_gerber_ct				= getFilename(output_file, ".crc");
		output_file_gerber_cb				= getFilename(output_file, ".crs");
		output_file_gerber_drill			= getFilename(output_file, ".drd");
		output_file_gerber_otl				= getFilename(output_file, ".otl");
		output_file_gerber_ref 				= getFilename(output_file, ".ref");
		output_file_gerber_fab 				= getFilename(output_file, ".fab");
		output_file_gerber_spec				= getFilename(output_file, "-specifications.txt");		
	} else if(gerber_format == 1) {		//Protel file naming
		//Output files to gerber directory
		output_file_gerber_copper_top 		= getFilename(output_file, ".GTL");
		output_file_gerber_copper_other 	= getFilename(output_file, ".G");
		output_file_gerber_copper_bottom 	= getFilename(output_file, ".GBL");
		output_file_gerber_st				= getFilename(output_file, ".GTS");
		output_file_gerber_sb				= getFilename(output_file, ".GBS");
		output_file_gerber_pt				= getFilename(output_file, ".GTO");
		output_file_gerber_pb				= getFilename(output_file, ".GBO");
		output_file_gerber_ct				= getFilename(output_file, ".GTP");
		output_file_gerber_cb				= getFilename(output_file, ".GBP");
		output_file_gerber_drill			= getFilename(output_file, ".txt");
		output_file_gerber_otl				= getFilename(output_file, ".GML");
		output_file_gerber_ref 				= getFilename(output_file, ".REF");
		output_file_gerber_fab 				= getFilename(output_file, ".FAB");
		output_file_gerber_spec				= getFilename(output_file, "-specifications.txt");
	}
	
	//Output files to CAD directory
	output_folder_idf = output_folder + cad_folder;

	//Output files for PNP file
	string ouput_file_pnp		= output_folder + pnp_folder + boardname;

	//Output files in eagle directory (Eagle + Spec file)
	output_file = output_folder + eagle_folder + boardname;
	output_folder_eagle 		= output_folder + eagle_folder;
	output_file_eagle_spec 	 	= getFilename(output_file, "-specifications+layer.txt");
	
	
	//Output files main directory (BOM + schematic PDF)
	output_file = output_folder + boardname;
	output_file_schematic_bw = getFilename(output_file, "-schematic-print.pdf");
	output_file_schematic_color = getFilename(output_file, "-schematic.pdf");		

	string measure_layer_top = "48 ";
	string measure_layer_bottom = "112 ";
	string names_layer_top = "25 ";
	string names_layer_bottom = "26 ";
	string values_layer_top = "27 ";
	string values_layer_bottom = "28 ";
	
	if(no_measures){
		measure_layer_top = "";
		measure_layer_bottom = "";
	}

	if(!parts_display_names){
		names_layer_top = "-" + names_layer_top;
		names_layer_bottom = "-" + names_layer_bottom;		
	}
	if(!parts_display_values){
		values_layer_top = "-" + values_layer_top;
		values_layer_bottom = "-" + values_layer_bottom;		
	}
	cmd += "EDIT .sch;";

	cmd += "SET CONFIRM YES;";

	if(renumber) {
		cmd += "RUN '"  + include_path + "Renumber.ulp';";
	}

	if(schematic_export) {
		string format = "A4 portrait ";
		if(schematic_format == 1) {
			format = "A3 landscape";
		}

		cmd+=updateFrameInformationSch();
		
		if(schematic_bw) {
			cmd += "SET CONFIRM YES;PRINT SHEETS ALL HIERARCHY PAPER " + format + " BLACK FILE '" + output_file_schematic_bw + "';";
		}
		if(schematic_color)	{
			cmd += "SET CONFIRM YES;PRINT SHEETS ALL HIERARCHY PAPER " + format + " -BLACK FILE '" + output_file_schematic_color + "';";
		}
	}

	if(pricing)	{
		sprintf(cmd, "%sRUN '%sPriceRequest.ulp';",cmd,include_path);	
	}

	cmd += "WRITE;";
	cmd += "EDIT .brd;";
	
	if(ec_export) {
		cmd += "SET CONFIRM YES;";
		sprintf(cmd, "%s WRITE \'" + output_folder + ecpanel_folder + boardname + "_ec.brd\';", cmd);
		sprintf(cmd, "%s EDIT \'" +  output_folder + ecpanel_folder + boardname + "_ec.brd\';", cmd);
		sprintf(cmd, "%s RUN '" + include_path + "EcPanel_V2.ulp';", cmd);
		
		ecpanel_path = output_folder + ecpanel_folder + boardname;
		
		cmd += "WRITE;";
		cmd += "SET CONFIRM YES;";	
		cmd += "EDIT '"+ getSystemFilename(".brd") +"';";
	}
	
	cmd += "WRITE;";
	
	if(measure) {
		sprintf(cmd,"%sRUN '%sMeasure.ulp' '%f';", cmd, include_path, minMeasureDiameter);
	}
	cmd += "WRITE;";
	
	if(drilltable || fabrication || stackup) {
		getMinMaxTemp();
		//The drilltable ulp has been repalced with the new fabrication ULP
		sprintf(cmd, "%s RUN '%sFabrication.ulp' %d %d %d \'%s\' \'%s\' \'%s\' \'%s\' \'%s\' \'%s\' \'%.2f\' \'%.2f\';", cmd, include_path, 
			fabrication, drilltable, stackup, 
			PcbType[board_type], pcbSpecColor[pcbimage_color], 
			pcbSpecSilkscreenColor[pcbimage_silkscreen_color], 
			pcbSpecPlating[pcbimage_plating],
			bname, (strtod(drcGetRule("mdCopperDimension"))==0.0)?"yes":"no",
			temp_min, temp_max
		);
	}
	cmd += "WRITE;";

	if(bom)	{
		sprintf(cmd, "%sRUN '"  + include_path + "BOM.ulp' '%s' -multiplier %f %s %s %s %s %s %s %s %f %f %f;",cmd, 
			getFilename(output_file, "-bom"), bom_quantity,  bom_xls?"-xls":"", 
			bom_csv?"-csv":"", bom_dbase3?"-dbase3":"", 
			bom_farnell?"-farnell":"", bom_shorten_names?"-short_names":"", 
			(!bom_display_package_type)?"-display_package_type":"", 
			bomToPDF?"-pdf":"", bom_offsetX, bom_offsetY, bom_width 
		);

		if(bomToPDF) {
			ExportSetup[0] = "BOM;"+boardname+"-bom;" + stringFromInt(lay_fabDoc[2]) + ";;" + stringFromInt(lay_fabDoc[0]) +"; BOM";
			cmd+=exportLayer(bomToPDF, 0, 1, "", output_folder,  "BOM");
		}
	}
	cmd += "WRITE;";

	
	if(EAGLE_VERSION>=9) {
		sprintf(cmd, "%s RUN '"  + include_path + "SilkGen.ulp';", cmd);
		cmd += "DISPLAY -"+stringFromInt(lay_dimension)+" -"+stringFromInt(lay_background)+" -"+stringFromInt(lay_empty)+";";
	}
	

	//We drop support for eagle < 7, so set confirm is ok
	cmd += "SET CONFIRM YES;";

	if(enable_export_png || enable_export_pdf){
		string mt = measure_layer_top;
		string mb = measure_layer_bottom;
		string ltx = "";
		string lbx = "";


		int stop_top = 1, stop_bot = 1, cream_top = 1, creap_bot = 1;

		if(parts_top_docu) {ltx = "51 ";}
		if(parts_bot_docu) {lbx = "52 ";}

		string layer_pdf = "", layer_image = "";
		if(pdf_keep_frame) {
			cmd += "LAYER " + stringFromInt(lay_fabDoc[0]) + " FabDoc1;";
			layer_pdf += stringFromInt(lay_fabDoc[0]) + " ";
		}
		//Quick fix, to get correct dimensions, for non mirrored views
		//layer_pdf += "-" + mb + " " + mt;

		int row = 0;
		//Index, Filenames, Default Layers, Layers PNG, Layers PDF, Drawing, png mirror
		ExportSetup[row++] = "L1 	;-l01-top		;1 17 18 20 " + mt + "										;" + layer_image + ";" + layer_pdf + "; Copper L1 - Top			;0";
		ExportSetup[row++] = "L2 	;-l02			;2 17 18 20 " + mt + "										;" + layer_image + ";" + layer_pdf + "; Copper L2				;0";
		ExportSetup[row++] = "L3 	;-l03			;3 17 18 20 " + mt + "										;" + layer_image + ";" + layer_pdf + "; Copper L3				;0";
		ExportSetup[row++] = "L4 	;-l04			;4 17 18 20 " + mt + "										;" + layer_image + ";" + layer_pdf + "; Copper L4				;0";
		ExportSetup[row++] = "L5 	;-l05			;5 17 18 20 " + mt + "										;" + layer_image + ";" + layer_pdf + "; Copper L5				;0";
		ExportSetup[row++] = "L6 	;-l06			;6 17 18 20 " + mt + "										;" + layer_image + ";" + layer_pdf + "; Copper L6				;0";
		ExportSetup[row++] = "L7 	;-l07			;7 17 18 20 " + mt + "										;" + layer_image + ";" + layer_pdf + "; Copper L7				;0";
		ExportSetup[row++] = "L8 	;-l08			;8 17 18 20 " + mt + "										;" + layer_image + ";" + layer_pdf + "; Copper L8				;0";
		ExportSetup[row++] = "L9 	;-l09			;9 17 18 20 " + mt + "										;" + layer_image + ";" + layer_pdf + "; Copper L9				;0";
		ExportSetup[row++] = "L10 	;-l10 			;10 17 18 20 " + mt + "										;" + layer_image + ";" + layer_pdf + "; Copper L10				;0";
		ExportSetup[row++] = "L11 	;-l11 			;11 17 18 20 " + mt + "										;" + layer_image + ";" + layer_pdf + "; Copper L11				;0";
		ExportSetup[row++] = "L12 	;-l12 			;12 17 18 20 " + mt + "										;" + layer_image + ";" + layer_pdf + "; Copper L12				;0";
		ExportSetup[row++] = "L13 	;-l13 			;13 17 18 20 " + mt + "										;" + layer_image + ";" + layer_pdf + "; Copper L13				;0";
		ExportSetup[row++] = "L14 	;-l14 			;14 17 18 20 " + mt + "										;" + layer_image + ";" + layer_pdf + "; Copper L14				;0";
		ExportSetup[row++] = "L15 	;-l15 			;15 17 18 20 " + mt + "										;" + layer_image + ";" + layer_pdf + "; Copper L15				;0";
		ExportSetup[row++] = "L16	;-l16-bot		;16 17 18 20 " + mb + "										;" + layer_image + ";" + layer_pdf + "; Copper L16 - Bottom		;1";
		ExportSetup[row++] = "PT 	;-parts-top		;20 " + ltx + tsilcsreenLayer + " " + mt + "				;" + layer_image + ";" + layer_pdf + "; Silkscreen - Top		;0";
		ExportSetup[row++] = "PB 	;-parts-bottom	;20 " + lbx + bsilcsreenLayer + " " + mb + "				;" + layer_image + ";" + layer_pdf + "; Silkscreen - Bottom		;1";
		ExportSetup[row++] = "ST 	;-stop-top		;20 29 " + mt + "											;" + layer_image + ";" + layer_pdf + "; Stopmask - Top			;0";
		ExportSetup[row++] = "SB 	;-stop-bottom	;20 30 " + mb + "											;" + layer_image + ";" + layer_pdf + "; Stopmask - Bottom		;1";
		ExportSetup[row++] = "CT 	;-paste-top		;20 31 " + mt + "											;" + layer_image + ";" + layer_pdf + "; Paste - Top				;0";
		ExportSetup[row++] = "CB 	;-paste-bottom	;20 32 " + mb + "											;" + layer_image + ";" + layer_pdf + "; Paste - Bottom			;1";
		ExportSetup[row++] = "FAB	;-fabrication 	;44 45 20 " + stringFromInt(lay_fabDoc[1]) + " "  + mt + "	;" + layer_image + ";" + layer_pdf + "; Fabrication				;0";
		ExportSetup[row++] = "MECH	;-construction 	;111 20 													;" + layer_image + ";" + layer_pdf + " -" + mt + "; Mechanical	;0";
		ExportSetup[row++] = "REF	;-reference 	;111 49														;" + layer_image + ";" + layer_pdf + "; Reference				;0";

		//Switch palette if export is enabled
		cmd += "SET PALETTE WHITE;";

		//Ratsnest all layers
		cmd += "DISPLAY ALL;";
		cmd += "RATSNEST;";

		//Set Layer fill to solid for all standard layers
		cmd += setLayerFill();

		//Export
		cmd += exportLayer(layout_top, 	enable_export_png, 	enable_export_pdf, output_folder_image, output_folder_pdf,  "L1");
		if(layout_inner_layer) {
			for(int i = 1; i < 15; i++) {
				cmd += exportLayer(board_layer[i] == 1, enable_export_png, 	enable_export_pdf, output_folder_image, output_folder_pdf,  "L" + stringFromInt(i+1));
			}
		}
		cmd += exportLayer(layout_bot, 	enable_export_png, 	enable_export_pdf, output_folder_image, output_folder_pdf,  "L16");
		cmd += exportLayer(parts_top, 	enable_export_png, 	enable_export_pdf, output_folder_image, output_folder_pdf,  "PT");
		cmd += exportLayer(parts_bot, 	enable_export_png, 	enable_export_pdf, output_folder_image, output_folder_pdf,  "PB");
		cmd += exportLayer(stop_top, 	enable_export_png, 	enable_export_pdf, output_folder_image, output_folder_pdf,  "ST");
		cmd += exportLayer(stop_bot, 	enable_export_png, 	enable_export_pdf, output_folder_image, output_folder_pdf,  "SB");
		cmd += exportLayer(cream_top, 	enable_export_png, 	enable_export_pdf, output_folder_image, output_folder_pdf,  "CT");
		cmd += exportLayer(creap_bot, 	enable_export_png, 	enable_export_pdf, output_folder_image, output_folder_pdf,  "CB");
		cmd += exportLayer(construction,enable_export_png, 	enable_export_pdf, output_folder_image, output_folder_pdf,  "MECH");
		cmd += exportLayer(reference, 	enable_export_png, 	enable_export_pdf, output_folder_image, output_folder_pdf,  "REF");
		cmd += exportLayer(drills, 		enable_export_png, 	enable_export_pdf, output_folder_image, output_folder_pdf,  "FAB");

		if(enable_export_png){
			//Crop
			if(crop_all){
				if(layout_top)	{cmd += pngCrop(output_folder_image, "L1");}
				if(layout_inner_layer) {
					for(int i = 1; i < 15; i++) {
						if(board_layer[i] == 1) {
								 cmd += pngCrop(output_folder_image, "L" + stringFromInt(i+1));
						}
					}
				}
				if(layout_bot)	{cmd += pngCrop(output_folder_image, "L16");}
				if(parts_top)	{cmd += pngCrop(output_folder_image, "PT");}
				if(parts_bot)	{cmd += pngCrop(output_folder_image, "PB");}
				if(stop_top)	{cmd += pngCrop(output_folder_image, "ST");}
				if(stop_bot)	{cmd += pngCrop(output_folder_image, "SB");}
				if(cream_top)	{cmd += pngCrop(output_folder_image, "CT");}
				if(creap_bot)	{cmd += pngCrop(output_folder_image, "CB");}				
				if(drills)		{cmd += pngCrop(output_folder_image, "FAB");}
				if(construction){cmd += pngCrop(output_folder_image, "MECH");}
				if(reference)	{cmd += pngCrop(output_folder_image, "REF");}
			}		
		}


		cmd += restoreLayerFill();

		cmd += "DISPLAY NONE; DISPLAY " + layers + ";";
		cmd += "SET PALETTE " + palette_name + ";";
		cmd += "RATSNEST;";

		//Export colored images
		if((pcbimage_top || pcbimage_bottom) && (enable_export_png || enable_export_pdf)) {
			sprintf(cmd, "%s RUN '"  + include_path + "ImageExport.ulp' %d %d %d '%s' '%s' %d '%s' '%s' %d %d %d '%s' '%s' '%s' '%s' '%s' '%s' %d %d %d;", cmd, 
				enable_export_png, (enable_export_pdf&&EAGLE_VERSION>=9),
				pcbimage_bottom, output_file_img_pcbb, output_file_pdf_pcbb,
				pcbimage_top, output_file_img_pcbt, output_file_pdf_pcbt,
				pcbImageResolutions[image_resolution],
				crop_all, mirror_bot, 
				pcbImagePcbColors[pcbimage_color],
				pcbImageCopperColors[pcbimage_color],
				pcbImageSilkscreenColors[pcbimage_silkscreen_color],
				pcbImagePlating[pcbimage_plating],
				tsilcsreenLayer, bsilcsreenLayer,
				board_format, pdf_keep_frame,
				cfg_enableAsync
			);

			if (pcbimage_top && enable_export_png && crop_all) 
				addToWaitinglist(output_file_img_pcbt);

			if (pcbimage_bottom && enable_export_png && crop_all) 
				addToWaitinglist(output_file_img_pcbb);
		}		
	}

	if(pdf_merge&&enable_export_pdf){
		sprintf(cmd,"%sRUN '%sMergePDF.ulp' %d '%s' '%s' %d %d '%s';\n", cmd, include_path, 
			output_date_folder, output_folder_pdf,
			getSystemFilename(".bat"), 
			(schematic_export&&schematic_color), (bomToPDF&&bom),
			lanGetText("dlg.pdf.footnote")
		);
	}

	if(idf_export) {
		cmd += "RUN '"  + include_path + "IDF.ulp' '" + output_folder_idf + "';";
	}

	if(gerber_export) {
		//Let the ulp retrieve the eagle executeable path once
		int count = 0;
		if(gerber_copper){
			for(int i = 0; i < 16; i++){
				if(board_layer[i] == 1){
					if(i == 0){	
						sprintf(cmd, "%s RUN '"  + include_path + "Gerber.ulp' 0 '%s' '%s' '%s' %d %d;", cmd,  getSystemFilename(".brd"), output_file_gerber_copper_top, getSystemFilename(".bat"), cfg_enableAsync, i+1);
						addToWaitinglist(output_file_gerber_copper_top + ".tmp");
					} else if(i == 15){
						sprintf(cmd, "%s RUN '"  + include_path + "Gerber.ulp' 0 '%s' '%s' '%s' %d %d;", cmd,  getSystemFilename(".brd"), output_file_gerber_copper_bottom, getSystemFilename(".bat"), cfg_enableAsync, i+1);
						addToWaitinglist(output_file_gerber_copper_bottom + ".tmp");
					} else {
						string tfname = "";
						sprintf(tfname, "%s%d", output_file_gerber_copper_other, i+1); 			
						sprintf(cmd, "%s RUN '"  + include_path + "Gerber.ulp' 0 '%s' '%s' '%s' %d %d;", cmd,  getSystemFilename(".brd"), tfname, getSystemFilename(".bat"), cfg_enableAsync, i+1);					
						addToWaitinglist(tfname + ".tmp");
					}
					count++;
				}			
			}
		}
		if(gerber_stc){ sprintf(cmd, "%s RUN '"  + include_path + "Gerber.ulp' 1 '%s' '%s' '%s' %d 1;", 			cmd,  getSystemFilename(".brd"), output_file_gerber_st, getSystemFilename(".bat"), cfg_enableAsync); addToWaitinglist(output_file_gerber_st + ".tmp"); }
		if(gerber_sts){ sprintf(cmd, "%s RUN '"  + include_path + "Gerber.ulp' 1 '%s' '%s' '%s' %d 0;", 			cmd,  getSystemFilename(".brd"), output_file_gerber_sb, getSystemFilename(".bat"), cfg_enableAsync); addToWaitinglist(output_file_gerber_sb + ".tmp"); }
		if(gerber_crc){ sprintf(cmd, "%s RUN '"  + include_path + "Gerber.ulp' 2 '%s' '%s' '%s' %d 1;", 			cmd,  getSystemFilename(".brd"), output_file_gerber_ct, getSystemFilename(".bat"), cfg_enableAsync); addToWaitinglist(output_file_gerber_ct + ".tmp"); }
		if(gerber_crs){ sprintf(cmd, "%s RUN '"  + include_path + "Gerber.ulp' 2 '%s' '%s' '%s' %d 0;", 			cmd,  getSystemFilename(".brd"), output_file_gerber_cb, getSystemFilename(".bat"), cfg_enableAsync); addToWaitinglist(output_file_gerber_cb + ".tmp"); }
		if(gerber_plc){ sprintf(cmd, "%s RUN '"  + include_path + "Gerber.ulp' 3 '%s' '%s' '%s' %d 1 %d %d %d %d;", cmd,  getSystemFilename(".brd"), output_file_gerber_pt, getSystemFilename(".bat"), cfg_enableAsync, silkscreen_tplace, silkscreen_tnames, silkscreen_tvalues, silkscreen_tdocu); addToWaitinglist(output_file_gerber_pt + ".tmp"); }
		if(gerber_pls){ sprintf(cmd, "%s RUN '"  + include_path + "Gerber.ulp' 3 '%s' '%s' '%s' %d 0 %d %d %d %d;", cmd,  getSystemFilename(".brd"), output_file_gerber_pb, getSystemFilename(".bat"), cfg_enableAsync, silkscreen_bplace, silkscreen_bnames, silkscreen_bvalues, silkscreen_bdocu); addToWaitinglist(output_file_gerber_pb + ".tmp"); }
		if(gerber_drd){ sprintf(cmd, "%s RUN '"  + include_path + "Gerber.ulp' 4 '%s' '%s' '%s' %d;",   			cmd,  getSystemFilename(".brd"), output_file_gerber_drill, getSystemFilename(".bat"), cfg_enableAsync); addToWaitinglist(output_file_gerber_drill + ".tmp"); }	
		if(gerber_otl){ sprintf(cmd, "%s RUN '"  + include_path + "Gerber.ulp' 5 '%s' '%s' '%s' %d;",   			cmd,  getSystemFilename(".brd"), output_file_gerber_otl, getSystemFilename(".bat"), cfg_enableAsync); addToWaitinglist(output_file_gerber_otl + ".tmp"); }	
		if(gerber_ref){ sprintf(cmd, "%s RUN '"  + include_path + "Gerber.ulp' 6 '%s' '%s' '%s' %d;",   			cmd,  getSystemFilename(".brd"), output_file_gerber_ref, getSystemFilename(".bat"), cfg_enableAsync); addToWaitinglist(output_file_gerber_ref + ".tmp"); }	
		if(gerber_fab){ sprintf(cmd, "%s RUN '"  + include_path + "Gerber.ulp' 7 '%s' '%s' '%s' %d;",   			cmd,  getSystemFilename(".brd"), output_file_gerber_fab, getSystemFilename(".bat"), cfg_enableAsync); addToWaitinglist(output_file_gerber_fab + ".tmp"); }	
	
		//Generate specification file
		sprintf(cmd, "%s RUN '"  + include_path + "Specification.ulp' '%s' %fmm '%s' %d %fum '%s' '%s' '%s';", cmd, output_file_gerber_spec, board_thickness, PcbType[board_type], count, board_copper_thickness, pcbSpecColor[pcbimage_color], pcbSpecSilkscreenColor[pcbimage_silkscreen_color], pcbSpecPlating[pcbimage_plating]); 		
	}

	if(pnp_export) {

		cmd += "EDIT .brd;";
		sprintf(cmd, "%s RUN '"  + include_path + "PickAndPlace.ulp' '%s' %d %d %d %d %f %f;", cmd, ouput_file_pnp + "-cpl.csv", pnp_top, pnp_bot, pnp_auto_offset, pnp_flip, pnp_offset_x, pnp_offset_y); 		
		sprintf(cmd, "%s RUN '"  + include_path + "BOM.ulp' '%s' -pnp ;", cmd, ouput_file_pnp);
	}

	cmd += "WRITE;";

	if(eagle_export) {

		sprintf(cmd, "%s RUN '"  + include_path + "Eagle.ulp' '%s' '%s';", cmd, getSystemFilename(".brd"), output_folder_eagle);
		sprintf(cmd, "%s RUN '"  + include_path + "Eagle.ulp' '%s' '%s';", cmd, getSystemFilename(".sch"), output_folder_eagle);

		//Count all used layers
		int count = 0;
		for(int i = 0; i < 16; i++){
			if(board_layer[i] == 1){	
				count++;
			}			
		}
		//Generate list of all layers for the silk screen
		string tsilk_layers = "";
		if(silkscreen_tplace){ tsilk_layers += "tPlace "; } 
		if(silkscreen_tnames){ tsilk_layers += "tNames "; } 
		if(silkscreen_tvalues){ tsilk_layers += "tValues "; } 
		if(silkscreen_tdocu){ tsilk_layers += "tDocu "; } 

		string bsilk_layers = "";
		if(silkscreen_bplace){ bsilk_layers += "bPlace "; } 
		if(silkscreen_bnames){ bsilk_layers += "bNames "; } 
		if(silkscreen_bvalues){ bsilk_layers += "bValues "; } 
		if(silkscreen_bdocu){ bsilk_layers += "bDocu "; } 
		

		//Generate specification file
		sprintf(cmd, "%s RUN '"  + include_path + "Specification.ulp' '%s' %fmm '%s' %d %fum '%s' '%s' '%s' '%s' '%s';", cmd, 
			output_file_eagle_spec, board_thickness, 
			PcbType[board_type], count, board_copper_thickness, 
			pcbSpecColor[pcbimage_color], 
			pcbSpecSilkscreenColor[pcbimage_silkscreen_color], 
			pcbSpecPlating[pcbimage_plating], tsilk_layers, bsilk_layers
		); 		
	}	
	
	cmd += "EDIT \'" + filepath + boardname + ".brd\'" + ";";

	cmd += "RUN '" + include_path + "RunBatch.ulp' '"+getSystemFilename(".bat")+"' '"+preCMD+"'";
	for(int i = 0; i<waitingcount; i++){
		cmd += " '" + waitingList[i] + "'";
	}
	cmd += ";";

	if(EAGLE_VERSION>=9){
		cmd+="SET Option.SignalNamesOnTraces "+cfgget("EAGLE:Option.SignalNamesOnTraces")+";";
		cmd+="SET Option.SignalNamesOnPads "+cfgget("EAGLE:Option.SignalNamesOnPads")+";";
		cmd+="SET Option.LiveDrc "+cfgget("EAGLE:Option.LiveDrc")+";";
	}
	else {
		cmd+="SET Option.SignalNames "+cfgget("EAGLE:Option.SignalNames")+";";
	}
	cmd+="SET Option.PadNames "+cfgget("EAGLE:Option.PadNames")+";";
	cmd+="SET Option.ViaLength "+cfgget("EAGLE:Option.ViaLength")+";";
	cmd+="SET Option.DisplayMode "+cfgget("EAGLE:Option.DisplayMode")+";";
	cmd+="SET Option.PolygonRatsnest "+cfgget("EAGLE:Option.PolygonRatsnest")+";\n";

	if(filesize("\'"+filepath+"fabrication.lbr\'")){
		cmd+="USE \'"+filepath+"fabrication.lbr\';";	//to prevent error messages the fabrication.lbr is loaded befor unloading
		cmd+="USE \'-"+filepath+"fabrication.lbr\';";
	}

	cmd += resetVew();

	cmd += "RUN '" + include_path + "EndMessage.ulp' '" + lanGetText("dlg.ExportCompleted") +"';\n";

	/*
	output("C:\\Work\\tmp\\tmp.scr","wt"){
		printf("%s\n", cmd);
	}
	*/

	exit(cmd);
}

void dialogImageSettings(){
	dlgDialog(lanGetText("headline.exportDlg")){

		dlgGroup(lanGetText("general.view")) {
			dlgHBoxLayout {
				dlgCheckBox(lanGetText("general.layout")+" Bot", layout_bot);
				dlgCheckBox(lanGetText("general.layout")+" Top", layout_top);
			};
			dlgCheckBox(lanGetText("settings.imag.innerLayer"), layout_inner_layer);

			dlgHBoxLayout {
				dlgCheckBox(lanGetText("settings.gerber.plc"), parts_top);
 				dlgCheckBox(lanGetText("settings.gerber.pls"), parts_bot);
			};

			dlgHBoxLayout {
	 			dlgCheckBox(lanGetText("settings.gerber.drill"), drills);
				dlgCheckBox(lanGetText("general.construction"), construction);
			};		
			dlgHBoxLayout {
				dlgCheckBox(lanGetText("settings.gerber.ref"), reference);
			};	
			dlgHBoxLayout{
				dlgCheckBox("Top "+lanGetText("general.view"), pcbimage_top);
				dlgCheckBox("Bottom "+lanGetText("general.view"), pcbimage_bottom);
			}
		};
		dlgGroup(lanGetText("general.filetype")) {
			dlgHBoxLayout{
				dlgCheckBox(lanGetText("settings.png"),enable_export_png);
				dlgCheckBox(lanGetText("settings.pdf"),enable_export_pdf);
			}
		}
		dlgTabWidget {
			dlgTabPage(lanGetText("headline.png")){
				dlgGroup("") {
					string tmp[];
					strsplit(tmp, lanGetText("comb.res"), ';');
					dlgComboBox(tmp, image_resolution);
					dlgCheckBox(lanGetText("settings.imag.crop"), crop_all);
					dlgLabel(lanGetText("dlg.imag.footnote"));
					dlgStretch(1);
				}
			}
			dlgTabPage(lanGetText("headline.pdf")) {
				dlgGroup("") {
					dlgCheckBox(lanGetText("settings.pdf.Frame"), 	pdf_keep_frame);
					dlgRadioButton("A4",board_format);
					dlgRadioButton("A3",board_format);

					if(strstr(OS_SIGNATURE,"Linux")>=0){
						pdf_merge=0;
					}
					else {
						dlgCheckBox(lanGetText("settings.pdf.Merge")+"*", 	pdf_merge);
						dlgLabel("* " + lanGetText("dlg.pfd.footnote"));
					}
					dlgStretch(1);
				}
			};
		}
		dlgGroup(lanGetText("headline.advancedSettings")) {
			dlgCheckBox(lanGetText("settings.imag.mirror"), mirror_bot);
			dlgCheckBox(lanGetText("settings.imag.noMeasures"), no_measures);	
			dlgCheckBox(lanGetText("settings.imag.alwaysExpT"), parts_top_docu);
			dlgCheckBox(lanGetText("settings.imag.alwaysExpB"), parts_bot_docu);
		};
		dlgPushButton(lanGetText("button.ok")) {
			dlgAccept();
		};
	};		
}

void dialogAddEditBomPreset(int set){
	if (set==0){
		dlgMessageBox(lanGetText("dlg.cantEdit"));
		return;
	}

	string name = (set==cfg_bomPreCount)?lanGetText("general.newPreset"):cfg_bomPreNames[set];
	real offX = (set==cfg_bomPreCount)?bom_offsetX:cfg_bomPreOffX[set];
	real offY = (set==cfg_bomPreCount)?bom_offsetY:cfg_bomPreOffY[set];
	real width = (set==cfg_bomPreCount)?bom_width:cfg_bomPreWidth[set];

	dlgDialog(lanGetText("button."+(set==cfg_bomPreCount)?"add":"edit")) {
		dlgVBoxLayout{
			dlgHBoxLayout {
				dlgLabel(lanGetText("general.name"));
				dlgStretch(1);
				dlgStringEdit(name);
			}
			dlgHBoxLayout {
				dlgLabel(lanGetText("settings.offset.x"));
				dlgStretch(1);
				dlgRealEdit(offX);
				dlgLabel("mm");
			}
			dlgHBoxLayout {
				dlgLabel(lanGetText("settings.offset.y"));
				dlgStretch(1);
				dlgRealEdit(offY);
				dlgLabel("mm");
			}
			dlgHBoxLayout {
				dlgLabel(lanGetText("settings.bom.width"));
				dlgStretch(1);
				dlgRealEdit(width);
				dlgLabel("mm");
			}

			dlgHBoxLayout {
				dlgPushButton(lanGetText("button.save")){
					cfg_bomPreNames[set] = name;
					cfg_bomPreOffX[set] = offX;
					cfg_bomPreOffY[set] = offY;
					cfg_bomPreWidth[set] = width;
					if(set==cfg_bomPreCount) {
						bomPreset=set;
						cfg_bomPreCount++;
					}
					saveConfig();
					dlgAccept();
				};
				dlgPushButton(lanGetText("button.cancel")){
					dlgAccept();
				};
			}
		}
	};
}

void dialogBomSettings(){
	dlgDialog(lanGetText("headline.exportDlg")){
		dlgGroup(lanGetText("general.bom")){

			dlgGroup(lanGetText("general.filetype")) {
				dlgHBoxLayout {
					dlgCheckBox("XLS", bom_xls);
				}
				dlgHBoxLayout {
					dlgCheckBox("CSV", bom_csv);
					dlgCheckBox("DBF(DBASE III)", bom_dbase3);
				}
				dlgHBoxLayout {
					dlgCheckBox("Farnell Bom", bom_farnell);
					dlgCheckBox("PDF", bomToPDF);
				}
			}
			dlgGroup(lanGetText("general.options")) {
				dlgHBoxLayout {
					dlgCheckBox("R1,R2,R3,R4 -> R1-4", bom_shorten_names);
					dlgCheckBox("SMD 0805 -> 0805", bom_display_package_type);
				}
				dlgHBoxLayout {
					dlgLabel(lanGetText("settings.bom.quantity"));
					dlgRealEdit(bom_quantity);
				}
			}
			dlgGroup(lanGetText("headline.bom.pdf")) {
				dlgHBoxLayout {
					if(cfg_bomPreNames[0]==""){
						cfg_bomPreNames[0]=lanGetText("general.last");
						cfg_bomPreOffX[0]=bom_offsetX;
						cfg_bomPreOffY[0]=bom_offsetY;
						cfg_bomPreWidth[0]=bom_width;
						cfg_bomPreCount++;
					}

					dlgComboBox(cfg_bomPreNames,bomPreset) {
						bom_offsetX = cfg_bomPreOffX[bomPreset];
						bom_offsetY = cfg_bomPreOffY[bomPreset];
						bom_width 	= cfg_bomPreWidth[bomPreset];
					};
					dlgStretch(1);
					dlgPushButton(lanGetText("button.add")){ 
						dialogAddEditBomPreset(cfg_bomPreCount);
						dlgRedisplay();
					};
					dlgPushButton(lanGetText("button.edit")){ 
						dialogAddEditBomPreset(bomPreset); 
						bom_offsetX = cfg_bomPreOffX[bomPreset];
						bom_offsetY = cfg_bomPreOffY[bomPreset];
						bom_width 	= cfg_bomPreWidth[bomPreset];
					};
					dlgPushButton(lanGetText("button.delete")){
						if (bomPreset==0){
							dlgMessageBox(lanGetText("dlg.cantEdit"));
							return;
						}

						for(int l=0, n=0;l<cfg_bomPreCount;l++){
							if(l!=bomPreset){
								cfg_bomPreNames[n]=cfg_bomPreNames[l];
								cfg_bomPreOffX[n]=cfg_bomPreOffX[l];
								cfg_bomPreOffY[n]=cfg_bomPreOffY[l];
								cfg_bomPreWidth[n]=cfg_bomPreWidth[l];
								n++;
							}
						}

						bomPreset--;
						cfg_bomPreCount--;

						cfg_bomPreNames[cfg_bomPreCount]="";

						bom_offsetX = cfg_bomPreOffX[bomPreset];
						bom_offsetY = cfg_bomPreOffY[bomPreset];
						bom_width 	= cfg_bomPreWidth[bomPreset];
					}
				}

				dlgHBoxLayout {
					dlgLabel(lanGetText("settings.offset.x"));
					dlgStretch(1);
					dlgRealEdit(bom_offsetX);
					dlgLabel("mm");
				}
				dlgHBoxLayout {
					dlgLabel(lanGetText("settings.offset.y"));
					dlgStretch(1);
					dlgRealEdit(bom_offsetY);
					dlgLabel("mm");
				}
				dlgHBoxLayout {
					dlgLabel(lanGetText("settings.bom.width"));
					dlgStretch(1);
					dlgRealEdit(bom_width);
					dlgLabel("mm");
				}
			};		
		};
		dlgPushButton(lanGetText("button.ok")) {
			dlgAccept();
		};
	};
}

void dialogSchematicSettings(){
	dlgDialog(lanGetText("headline.exportDlg")){
		dlgGroup(lanGetText("headline.exportDlg")){
			dlgGroup(lanGetText("general.format")) {
				dlgRadioButton("A4", schematic_format);
				dlgRadioButton("A3", schematic_format);
			}
			dlgGroup(lanGetText("general.options")) {
				dlgCheckBox(lanGetText("settings.schematic.bw"), schematic_bw);	
				dlgCheckBox(lanGetText("settings.schematic.color"), schematic_color);		
			}		
		};
		dlgPushButton(lanGetText("button.ok")) {
			dlgAccept();
		};
	};
}

void dialogGerberSettings(){
	dlgDialog(lanGetText("headline.exportDlg")){
		dlgGroup(lanGetText("headline.gerber.naming")){
			dlgRadioButton(lanGetText("settings.gerber.eagle"),  gerber_format);
			dlgRadioButton(lanGetText("settings.gerber.protel"), gerber_format);
		}
		dlgGroup(lanGetText("headline.gerber.RS274X")) {
			dlgCheckBox(lanGetText("settings.gerber.copper") + " (.sol, .gXX, .cmp) ", 	gerber_copper);
			dlgCheckBox(lanGetText("settings.gerber.stc") + " (.stc)", 					gerber_stc);	
			dlgCheckBox(lanGetText("settings.gerber.sts") + " (.sts)", 					gerber_sts);
			dlgCheckBox(lanGetText("settings.gerber.plc") + " (.plc)", 					gerber_plc);	
			dlgCheckBox(lanGetText("settings.gerber.pls") + " (.pls)", 					gerber_pls);
			dlgCheckBox(lanGetText("settings.gerber.crc") + " (.crc)", 					gerber_crc);	
			dlgCheckBox(lanGetText("settings.gerber.crs") + " (.crs)", 					gerber_crs);	
			dlgCheckBox(lanGetText("settings.gerber.otl") + " (.otl)", 					gerber_otl);		
			dlgCheckBox(lanGetText("settings.gerber.ref") + " (.ref)",					gerber_ref);	
			dlgCheckBox(lanGetText("settings.gerber.fab") + " (.fab)",					gerber_fab);				
		}
		dlgGroup(lanGetText("headline.gerber.excellon")) {		
	 		dlgCheckBox(lanGetText("settings.gerber.drill")+" (.drd, .drl)", 			gerber_drd);	
		};		
		dlgPushButton(lanGetText("button.ok")) {
			dlgAccept();
		};
	};
}

void dialogPnpSettings(){
	dlgDialog(lanGetText("headline.exportDlg")){
		dlgGroup(lanGetText("general.side")) {
			dlgCheckBox("Top", 					pnp_top);
			dlgCheckBox("Bottom", 				pnp_bot);			
		};	
		dlgPushButton(lanGetText("button.ok")) {
			dlgAccept();
		};
	};
}

void dialogFabricationSettings() {
	dlgDialog(lanGetText("headline.exportDlg")) {
		dlgVBoxLayout {
			dlgGroup(lanGetText("headline.boardInfo")) {
				dlgCheckBox(lanGetText("settings.measure"),measure);
				dlgHBoxLayout{dlgLabel(lanGetText("settings.minViaSize")); dlgStretch(1); dlgRealEdit(minMeasureDiameter, 0.0, 100000.0); dlgLabel("mm");}
				dlgCheckBox(lanGetText("settings.drilltable"),drilltable); 
				dlgCheckBox(lanGetText("settings.fabrication"),fabrication);
				dlgCheckBox(lanGetText("settings.stackup"),stackup);
			}
			dlgPushButton(lanGetText("button.ok")) {dlgAccept();};
		}
	};
}

void mainManu(){
	//In Eagle Version > 7, we need to have a fixed
	//an absolute Path to our ULPs as Eagle otherwhise
	//wont find it
	include_path = getUlpDir(include_path);
	

	//Load/Reload DRC rule files
	if(argc > 1 && argv[1] == "drcLoaded"){
		drcLoadRules(getSystemFilename(drc_file), 0);
	} 
	else if(argc > 1 && argv[1] == "execute"){
		//Load the users project settings
		loadUsersettings();
		loadConfig();

		lanLoadText(cfg_textLanguage);

		drcLoadRules(getSystemFilename(drc_file), 0);

		if(argc==2){
			int error=0;

			board(B){
				B.errors(ER){
					if((ER.state!=ERROR_STATE_APPROVED) && (ER.type!=ERROR_TYPE_NONE)) {
						error++;
					}
				}
			}

			if(error!=0){
				lanLoadText(cfg_textLanguage);
				int opt=dlgMessageBox(lanGetText("dlg.drcError"),lanGetText("button.continue"),lanGetText("button.cancel"));
				if(opt){
					exit("");
				}
			}
		}
		else{
			UI_LESS=1;
		}
		
		enable_export_pdf = enable_export_pdf && enable_export_image;
		enable_export_png = enable_export_png && enable_export_image;

		measure = measure && board_info;
		drilltable = drilltable && board_info;
		fabrication = fabrication && board_info;
		stackup = stackup && board_info;

		export();
	}
	else if(argc > 1 && argv[1] == "uiLess"){
		drcLoadRules(getSystemFilename(drc_file), 2);
	} 
	else {
		drcLoadRules(getSystemFilename(drc_file), 1);		
	}

	//Load the users project settings
	loadUsersettings();

	loadDRCSettings();

	loadConfig();

	lanLoadText(cfg_textLanguage);

	//Create the main dialog
	int dialog = dlgDialog(ULP_VERSION){
		dlgHBoxLayout {
			dlgVBoxLayout {
				dlgGroup(lanGetText("headline.general.execution")) {
					dlgGridLayout{ 
						dlgCell(0,0) dlgLabel(lanGetText("settings.general.boardTitle"));
						dlgCell(0,1) dlgStringEdit(board_title);
						dlgCell(1,0) dlgLabel(lanGetText("settings.general.boardSubtitle"));
						dlgCell(1,1) dlgStringEdit(board_subtitle);
					};
				}
				dlgGroup(lanGetText("headline.general.execution")) {
					dlgGridLayout{ 
						dlgCell(0,0) dlgLabel(lanGetText("settings.general.boardThickness"));
						string tmp1;
						sprintf(tmp1,"%g mm",board_thickness);
						dlgCell(0,1) dlgLabel(tmp1);
					 
						dlgCell(1,0) dlgLabel(lanGetText("settings.general.boardMaterial"));
						dlgCell(1,1) dlgComboBox(PcbType, board_type);
					
						dlgCell(2,0) dlgLabel(lanGetText("settings.general.pcbColor"));
						string tmp2[];
						strsplit(tmp2, lanGetText("comb.pcbColor"), ';');
						dlgCell(2,1) dlgComboBox(tmp2, pcbimage_color);
					
						dlgCell(3,0) dlgLabel(lanGetText("settings.general.siscColor"));
						string tmp3[];
						strsplit(tmp3, lanGetText("comb.pcbSiScColor"), ';');
						dlgCell(3,1) dlgComboBox(tmp3, pcbimage_silkscreen_color);
					
						dlgCell(4,0) dlgLabel(lanGetText("settings.general.surface"));
						string tmp4[];
						strsplit(tmp4, lanGetText("comb.pcbPlating"), ';');
						dlgCell(4,1) dlgComboBox(tmp4, pcbimage_plating);
					};								
				}
				dlgGroup(lanGetText("headline.usedLayers")) {
					dlgGridLayout {
						dlgCell(0,0) dlgLabel(lanGetText("general.layer"));
						dlgCell(0,1) dlgLabel(lanGetText("general.name"));
						dlgCell(0,2) dlgLabel(lanGetText("settings.general.copperThickness"));

						for(int i=0, l=1; i<16; i++){
							if(board_layer[i]){
								string nr, th;
								sprintf(nr,"%02d",(i+1));
								sprintf(th,"%0.1f µm",copper_layer_thickness[i]);
								dlgCell(l,0) dlgLabel(nr);
								dlgCell(l,1) dlgLabel(copper_layer_Name[i]);
								dlgCell(l,2) dlgLabel(th);
								l++;
							}
						}
					}
				}
				dlgGroup(lanGetText("headline.general.siscTop")) {
					dlgHBoxLayout {
						dlgCheckBox("tPlace", silkscreen_tplace);
						dlgCheckBox("tNames", silkscreen_tnames);
		 				dlgCheckBox("tValues", silkscreen_tvalues);
		 				dlgCheckBox("tDocu", silkscreen_tdocu);
					};
				}
				dlgGroup(lanGetText("headline.general.siscBot")) {
					dlgHBoxLayout {
						dlgCheckBox("bPlace", silkscreen_bplace);
						dlgCheckBox("bNames", silkscreen_bnames);
		 				dlgCheckBox("bValues", silkscreen_bvalues);
		 				dlgCheckBox("bDocu", silkscreen_bdocu);
					};			
				}
				dlgStretch(1);
			}
			dlgVBoxLayout {
				dlgGroup(lanGetText("headline.staps")){
					dlgHBoxLayout {dlgCheckBox(lanGetText("settings.renumber"), renumber); dlgStretch(1);}
					dlgHBoxLayout {dlgCheckBox(lanGetText("settings.schematic"),schematic_export); dlgStretch(1); dlgPushButton("⚙"){dialogSchematicSettings();}; };
					dlgHBoxLayout {dlgCheckBox(lanGetText("settings.boardInfo"),board_info); dlgStretch(1); dlgPushButton("⚙"){dialogFabricationSettings();}; };
					dlgHBoxLayout {dlgCheckBox(lanGetText("settings.image"),enable_export_image); dlgStretch(1); dlgPushButton("⚙"){dialogImageSettings();}; };
					dlgHBoxLayout {dlgCheckBox(lanGetText("settings.pricing"),pricing); dlgStretch(1); };
					dlgHBoxLayout {dlgCheckBox(lanGetText("settings.bom"),bom); dlgStretch(1); dlgPushButton("⚙"){dialogBomSettings();}; };
					dlgHBoxLayout {dlgCheckBox(lanGetText("settings.idf"),idf_export); dlgStretch(1); };
					dlgHBoxLayout {dlgCheckBox(lanGetText("settings.gerber"),gerber_export); dlgStretch(1); dlgPushButton("⚙"){dialogGerberSettings();}; };
					dlgHBoxLayout {dlgCheckBox(lanGetText("settings.pnp"),pnp_export); dlgStretch(1); dlgPushButton("⚙"){dialogPnpSettings();}; };		
					dlgHBoxLayout {dlgCheckBox(lanGetText("settings.eagle"),eagle_export); dlgStretch(1); };
					dlgHBoxLayout {dlgCheckBox(lanGetText("settings.panel"),ec_export); dlgStretch(1); };
				}
				dlgGroup(lanGetText("settings.output")){
					dlgHBoxLayout {
			 			dlgLabel(lanGetText("settings.output"));
			  			dlgStringEdit(output_folder);
						dlgPushButton("📁"){
							if(output_folder == "./"){
								output_folder = bname;
							}
							output_folder = dlgDirectory(lanGetText("headline.selectOutput"), output_folder);
							output_folder += "/";
						}
			  		}
					//dlgHBoxLayout {dlgCheckBox(lanGetText("settings.DateFolder"), output_date_folder); dlgStretch(1);}		
				}
				dlgGroup("Easy Setup"){
					if(checkAll(getSystemFilename(drc_file))){
						dlgLabel(lanGetText("dlg.Check.err"));
						dlgHBoxLayout{
							dlgStretch(1);
							dlgPushButton(lanGetText("general.yes")){
								saveUsersettings();
								exit("RUN '" + getUlpDir("../EasySetup.ulp") + "' '" + getSystemFilename(drc_file) + "';");
							};
						}
					}
					else{
						dlgLabel("<html>" + lanGetText("dlg.Check.noErr") + "</html>");
					}
				}
				dlgStretch(1);
			}
		}
		dlgHBoxLayout {
			dlgStretch(1); 
			dlgPushButton(lanGetText("button.ok")) {
				saveUsersettings();

				string cmd = "";
				cmd += "DRC;";

				cmd += "DISPLAY NONE 20;";
				cmd += "RUN '" + include_path + "ZoomVisible.ulp';";
				cmd += "SET CONFIRM YES;";
				cmd += "EXPORT IMAGE '" + bname + "window.png' WINDOW 10;";
				cmd += "EXPORT IMAGE '" + bname + "all.png' 10;";
				cmd += "DISPLAY LAST;";
				cmd += "WINDOW LAST;";

				cmd += "RUN '" + getUlpDir("../ExportPro.ulp") + "' execute;";
				exit(cmd);
			};
			dlgPushButton(lanGetText("button.cancel")) {
				saveUsersettings();
				exit(EXIT_SUCCESS);
			};
			dlgPushButton("⚙") {
				if(editUserConfig()){
					saveUsersettings();
					exit("RUN '" + getUlpDir("../ExportPro.ulp") + "' drcLoaded;");
				}
			};
			dlgStretch(1); 
		}
		dlgHBoxLayout {
			dlgStretch(1); 
			dlgLabel("(c) Copyright 2007-2019, Bernhard Wörndl-Aichriedler");
			dlgStretch(1); 
		}
	};	
}


//Call main menu
mainManu();
