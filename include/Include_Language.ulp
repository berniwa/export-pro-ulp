/**
 * This ULP will handle multilanguage support for the main gui		
 * 
 * @author 		Bernhard Wörndl-Aichriedler <bwa@xdevelop.at>
 * @author 	  	Tobias Hofer <thofer@xdevelop.at>
 * @copyright	2011-2019, Bernhard Wörndl-Aichriedler
 * @license 	BSD-3-Clause
 */
#include "Include_String.ulp"

string  lanContent = "";
int 	lanLines = 0;
string  lan="";

void lanLoadText(string languageFile) {
	languageFile = "../Languages/" + languageFile;
	lan=getUlpDir(languageFile);

	if (!filesize(lan)) {
		languageFile="../Languages/en.txt";
		lan=getUlpDir(languageFile);
	}

	lanLines = fileread(lanContent, lan);
}

/* Parameters look like: grid 5 mm, outline 5 x 5 mm */
string lanWord(string parameter, string haystack) {
	string data = "";

	parameter = parameter + " =";

	int start = strstr(haystack, parameter, 0);
	int len = strlen(parameter) + 1;
	int end = 0;

	if(start != -1) {
		end = strstr(haystack, "\n", start);
		end = end==-1?strlen(haystack):end;

		data = strsub(haystack, start + len , end-(start+len));
	}

	return stringTrim(data);
}

string lanGetText(string name) {
	string result = "";
	for(int i = 0; i < lanLines; i++) {
		result = lanWord(name, lanContent);
		if(result != "") {
			return result;
		}
	}

	return name+" was not found in language.txt";
}
