/**
 * This ULP handles the eagle design rules and allows
 * reading design rule values
 *
 * @author 		Bernhard Wörndl-Aichriedler <bwa@xdevelop.at>
 * @author 		Tobias Hofer <thofer@xdevelop.at>
 * @copyright	2019-2019, Bernhard Wörndl-Aichriedler
 * @license 	BSD-3-Clause
 */
#include "Include_String.ulp"

string  drcContent = "";
int 	drcLines = 0;

string drcGetDefaultFilename(){
	string bname = "";

	project.board(B)
	{
		bname = filesetext(B.name, "-exportpro.dru");
	}

	return bname;
}

/**
 * Load Design rules
 */
void drcLoadRules(string drc, int load){
	//string data[];
	if(load==0){
		//Load DRC file
		drcLines = fileread(drcContent, drc);
	}
	else if(load == 1){
		//Export DRC file and re-run ULP
		string cmd = "";

		if(schematic){
			cmd += "EDIT .brd;";
		}

		cmd += "DRC SAVE \'" + drc + "\';";
		cmd += "RUN '" + getUlpDir("../ExportPro.ulp") + "' drcLoaded;";

		exit(cmd);
	}
	else if(load==2){
		//Export DRC file and re-run ULP in execute mode
		string cmd = "";

		if(schematic){
			cmd += "EDIT .brd;";
		}

		cmd += "DRC SAVE \'" + drc + "\';";

		cmd += "DISPLAY NONE 20;";
		cmd += "RUN '" +  getUlpDir("Include_ZoomVisible.ulp") + "';";
		cmd += "SET CONFIRM YES;";
		cmd += "EXPORT IMAGE '" + filedir(drc) + "window.png' WINDOW 10;";
		cmd += "EXPORT IMAGE '" + filedir(drc) + "all.png' 10;";
		cmd += "DISPLAY LAST;";
		cmd += "WINDOW LAST;";

		cmd += "RUN '" + getUlpDir("../ExportPro.ulp") + "' execute drcIgnore;";

		exit(cmd);
	}
}

/* Parameters look like: grid 5 mm, outline 5 x 5 mm */
string drcValue(string parameter, string haystack){
	string data = "";

	parameter = parameter + " =";

	int start = strstr(haystack, parameter, 0);
	int len = strlen(parameter) + 1;
	int end = 0;

	if(start != -1)
	{
		end = strstr(haystack, "\n", start);
		end = end==-1?strlen(haystack):end;

		data = strsub(haystack, start + len , end-(start+len));
	}

	return stringTrim(data);
}

string drcGetRule(string name){
	string result = "";
	for(int i = 0; i < drcLines; i++)
	{
		result = drcValue(name, drcContent);
		if(result != "")
		{
			return result;
		}
	}
	return "";
}
