/**
 * This ULP mirrors monochrome images
 *
 * @author    Bernhard Wörndl-Aichriedler <bwa@xdevelop.at>
 * @author    Tobias Hofer <thofer@xdevelop.at>
 * @copyright 2009-2019, Bernhard Wörndl-Aichriedler
 * @license   BSD-3-Clause
 */

#include "Include_Misc.ulp";

if(OS_SIGNATURE == "Windows_7" || OS_SIGNATURE == "Windows_8" || OS_SIGNATURE == "Windows_10")	
{	
	string WinProgPath = getUlpDir("../bin/PNGMirrorCrop.exe");
	string Space = " ";
	string Param1 = "\"" + argv[1] + "\"";
	string Param2 = " 0 1";		//1st Method: <name> <crop> <mirror>
	string CallOfWinProg = WinProgPath + Space + Param1 + Param2;
  
  //dlgMessageBox(argv[2]);
  output(argv[2],"at"){
    printf(CallOfWinProg+"\n");
  }
}
else if(OS_SIGNATURE == "Linux")
{
	string WinProgPath = getUlpDir("../bin/PNGMirrorCrop-lin32.run");
	system("chmod +x " + WinProgPath);	//getting execute-rights
	string Space = " ";
	string Param1 = "\"" + argv[1] + "\"" ;
	string Param2 = " 0 1";		//1st Method: <name> <crop> <mirror>
	string CallOfWinProg = WinProgPath + Space + Param1 + Param2;
  
  //dlgMessageBox(argv[2]);
  output(argv[2],"at"){
    printf(CallOfWinProg+"\n");
  }
}
else
{
  dlgMessageBox("Unfortunately PNG mirroring is not supported on your plattform");
}
