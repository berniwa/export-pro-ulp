/**
 * This ULP simply copies the eagle files to a backup directory
 *
 * @author 		Bernhard Wörndl-Aichriedler <bwa@xdevelop.at>
 * @author 		Tobias Hofer <thofer@xdevelop.at>
 * @copyright	2013-2019, Bernhard Wörndl-Aichriedler
 * @license 	BSD-3-Clause
 */

#usage ""
string tmp =filedir(argv[1]); //tmp[0] is the drive indicator
system("CMD.EXE /C " + tmp[0] + ": & cd \"" + tmp + "\" & copy \"" + argv[1] + "\" \"" +  argv[2] + "\"");
