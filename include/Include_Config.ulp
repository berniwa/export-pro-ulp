/**
 * This ULP handles the default ULP configuration
 *
 * @author 		Tobias Hofer <thofer@xdevelop.at>
 * @author 		Bernhard Wörndl-Aichriedler <bwa@xdevelop.at>
 * @copyright	2009-2019, Bernhard Wörndl-Aichriedler
 * @license 	BSD-3-Clause
 */

#include "Include_Misc.ulp";
#include "Include_Language.ulp";
#include "Include_String.ulp";

string 
cfg_textLanguage = "", 
cfg_userName = "", 
cfg_shortUserName = "",
cfg_pricingURL = "http://eagle.berniwa.com/price.php",
cfg_defaultTolerance = "1%",
cfg_defaultVoltage = "50V"
;

int 
cfg_enableAsync = 1,
cfg_ulpInMenu = 0
;

char exp_window = 0; //png export window or drawing

int 
lay_dimension = 123,
lay_background = 124,
lay_empty = 127,
lay_fabDoc[] = {153, 154, 155}; //fabDoc1 - fabDoc3 

//variables for bom export presets
string 	cfg_bomPreNames[];
real 	cfg_bomPreOffX[];
real 	cfg_bomPreOffY[];
real 	cfg_bomPreWidth[];
int 	cfg_bomPreCount;

void saveConfig() {
	cfgset("ULP:ExportPro.language",cfg_textLanguage);
	cfgset("ULP:ExportPro.userName",cfg_userName);
	cfgset("ULP:ExportPro.shortUserName",cfg_shortUserName);
	cfgset("ULP:ExportPro.pricingURL",cfg_pricingURL);
	cfgset("ULP:ExportPro.defaultTolerance",cfg_defaultTolerance);
	cfgset("ULP:ExportPro.defaultVoltage",cfg_defaultVoltage);
	cfgset("ULP:ExportPro.enableAsync",(cfg_enableAsync?"1":"0"));
	cfgset("ULP:ExportPro.ulpInMenu",(cfg_ulpInMenu?"1":"0"));

	if(cfg_bomPreNames[1]!=""){
		string data="";
		int i=1;
		while(1){
			sprintf(data,"%s%s,%f,%f,%f", data, cfg_bomPreNames[i], cfg_bomPreOffX[i], cfg_bomPreOffY[i], cfg_bomPreWidth[i]);

			if(cfg_bomPreNames[++i]){
				data+=";";
			}
			else {
				break;
			}
		}
		cfgset("ULP:ExportPro.bomPresets",data);
	}
}

string getScrPath(){
	string pathSCR="";
	for(int i=0;path_scr[i];i++){
		pathSCR = path_scr[i]+"/eagle.scr";
		
		if(filesize(pathSCR)){
			break;
		}
	}
	return pathSCR;
}

string isNotMenu(){
	string pathSCR = getScrPath();
	string pathO="";
	string scrI;

	fileread(scrI,pathSCR);
	//searching for 2 entrys in the eagle script
	if(strstr(scrI,argv[0],(strstr(scrI,argv[0]) + 1))==-1){ 
		pathO=pathSCR;
	}

	return pathO;
}

void setToMenu(){
	string pathULP = filedir(argv[0]);


	if(strstr(pathULP,"/include")!=-1) {
		pathULP += "/../";
	}

	string pathSCR = isNotMenu();
	if(pathSCR){
		string scr;
		int index;


		fileread(scr,pathSCR);
		
		index = strstr(scr,"MENU",strstr(scr,"BRD:"))+5;
		scr = stringApend(scr, "'Export Pro: RUN "+pathULP+"ExportPro.ulp;'\\\n\t'Select Part: RUN "+pathULP+"SelectPart.ulp;'\\\n\t",index);
		
		index = strstr(scr,"MENU",strstr(scr,"SCH:"))+5;
		scr = stringApend(scr, "'Export Pro: RUN "+pathULP+"ExportPro.ulp;'\\\n\t'Select Part: RUN "+pathULP+"SelectPart.ulp;'\\\n\t",index);

		scr = stringReplace(scr,"SCH:","SCH:\nSET CONTEXT instance 'Select Part' 'run "+getUlpDir("../SelectPart.ulp")+" 1';");

		output(pathSCR){
			printf(scr);
		}
		
		/*		//attempt to updaite the manu instently without restarting the editor window
		string re = "SCRIPT \"" + pathSCR + "\";\nRUN";
		for(int i = 0;argv[i];i++)
			re += " \"" + argv[i] + "\"";

		re += ";";
		exit(re);
		*/
	}	
}

void removeFromMenu(){
	string pathSCR = getScrPath();
	string scr, tmp;
	int start, end;

	fileread(scr,pathSCR);
	
	start = strstr(scr,"'Export Pro",strstr(scr,"MENU",strstr(scr,"BRD:")));
	end = strstr(scr, ";'",strstr(scr, "'Select Part", start))+5;
	scr = stringCutout(scr, start, end);

	start = strstr(scr,"'Export Pro",strstr(scr,"MENU",strstr(scr,"SCH:")));
	end = strstr(scr, ";'",strstr(scr, "'Select Part", start))+5;
	scr = stringCutout(scr, start, end);

	start = strstr(scr,"'SelectPart",strstr(scr,"SET CONTEXT",strstr(scr,"BRD:")));
	tmp = strsub(scr, 0, start);				//to just remove the one entery
	start = strrstr(tmp,"SET CONTEXT");
	end = strstr(scr, ";", start)+2;
	scr = stringCutout(scr, start, end);

	//dlgMessageBox(scr);

	output(pathSCR){
		printf(scr);
	}
}

void updateManu(){
	removeFromMenu();
	setToMenu();
}

char editUserConfig(){
	if (!filesize(getUlpDir("../Languages/"+cfg_textLanguage))) {
		cfg_textLanguage=language()+".txt";
		if (!filesize(getUlpDir("../Languages/"+cfg_textLanguage))) {
			cfg_textLanguage="en.txt";
		}
	}

	char update=0;
	string languages[];
	int languageCount = fileglob(languages,getUlpDir("../Languages/*.txt"));
	int n = 0;

	for(int i=0; i<languageCount; i++){
		languages[i] = filename(languages[i]);
		if(strstr(cfg_textLanguage,languages[i])!=-1){
			n=i;
		}
		languages[i] = strsub(languages[i],0,(strrstr(languages[i],".txt")));
	}

	cfg_textLanguage = languages[n]+".txt";
	string lastLanguage = cfg_textLanguage;
	lanLoadText(cfg_textLanguage);

	if(!cfg_userName && !cfg_ulpInMenu){ //first start of the ulp
		int opt = dlgMessageBox(lanGetText("dlg.add2Menu"),lanGetText("general.yes"),lanGetText("general.no"));
		if (opt == 0){
			cfg_ulpInMenu = 1;
			setToMenu();
		}
	} 

	real tol = strtod(cfg_defaultTolerance);
	real volt = strtod(cfg_defaultVoltage);

	dlgDialog(lanGetText("settings.general")) {
		dlgVBoxLayout {
			dlgGroup(lanGetText("settings.general")) {
				dlgGridLayout {
					dlgCell(0, 0) dlgLabel(lanGetText("general.language")+":");
					dlgCell(0, 1) dlgComboBox(languages,n){
						cfg_textLanguage = languages[n]+".txt";
						update=1;
					};

					dlgCell(1, 0) dlgLabel(lanGetText("grneral.userName")+":");
					dlgCell(1, 1) dlgStringEdit(cfg_userName);
					dlgCell(2, 0) dlgLabel(lanGetText("general.shortName")+":");
					dlgCell(2, 1) dlgStringEdit(cfg_shortUserName);
					dlgCell(3, 0) dlgLabel(lanGetText("general.pricingURL")+":");
					dlgCell(3, 1) dlgStringEdit(cfg_pricingURL);
					dlgCell(4, 0) dlgLabel(lanGetText("settings.default.tolerance")+":");
					dlgCell(4, 1) dlgHBoxLayout {dlgRealEdit(tol); dlgLabel("%");}
					dlgCell(5, 0) dlgLabel(lanGetText("settings.default.voltage")+":");
					dlgCell(5, 1) dlgHBoxLayout {dlgRealEdit(volt); dlgLabel("V");}
					dlgCell(6, 0) dlgLabel(lanGetText("settings.general.async"));
					dlgCell(6, 1) dlgCheckBox("",cfg_enableAsync);
				}
				if(isNotMenu()){
					dlgPushButton(lanGetText("settings.menu")){
						cfg_ulpInMenu = 1;
						setToMenu();
					};
				}
			}

			dlgHBoxLayout{
			dlgPushButton(lanGetText("button.ok")){dlgAccept();};
				dlgPushButton(lanGetText("button.cancel")){
					update=0;
					cfg_textLanguage = lastLanguage;
					dlgReject();
				};
			}
		}
	};

	sprintf(cfg_defaultTolerance,"%g%%",tol);
	sprintf(cfg_defaultVoltage,"%gV",volt);

	saveConfig();
	return update;
}

void loadConfig(){
	cfg_textLanguage 		= cfgget("ULP:ExportPro.language" ,(language()+".txt"));
	cfg_userName 			= cfgget("ULP:ExportPro.userName");
	cfg_shortUserName 		= cfgget("ULP:ExportPro.shortUserName");
	cfg_pricingURL 			= cfgget("ULP:ExportPro.pricingURL", cfg_pricingURL);
	cfg_defaultTolerance 	= cfgget("ULP:ExportPro.defaultTolerance", cfg_defaultTolerance);
	cfg_defaultVoltage 		= cfgget("ULP:ExportPro.defaultVoltage", cfg_defaultVoltage);
	cfg_enableAsync 		= strtol(cfgget("ULP:ExportPro.enableAsync", (cfg_enableAsync?"1":"0")));
	cfg_ulpInMenu 		= strtol(cfgget("ULP:ExportPro.ulpInMenu", (cfg_ulpInMenu?"1":"0")));
	string tmp 				= cfgget("ULP:ExportPro.bomPresets");

	if(isNotMenu() && cfg_ulpInMenu){
		updateManu();
	}

	if(tmp!=""){
		string tmpa[];
		string tmpb[];
		cfg_bomPreCount = strsplit(tmpa,tmp,';');

		cfg_bomPreNames[0]="";

		for(int n=0; n<cfg_bomPreCount; n++){
			strsplit(tmpb,tmpa[n],',');

			cfg_bomPreNames[n+1]=tmpb[0];
			cfg_bomPreOffX[n+1]=strtod(tmpb[1]);
			cfg_bomPreOffY[n+1]=strtod(tmpb[2]);
			cfg_bomPreWidth[n+1]=strtod(tmpb[3]);
		}
	}

	if(cfg_userName=="") {
		//first time the ulp is started
		editUserConfig();
	}

	project.board(B){
		int all = filesize(filedir(B.name) + "all.png");
		int window = filesize(filedir(B.name) + "window.png");
		if (all && window){
			exp_window = (window <= all)?1:0;

			string cmd = "CMD.EXE /C ";
			cmd += "DEL /F /Q \"" + stringReplace(filedir(B.name),"/","\\") + "all.png\" & ";
			cmd += "DEL /F /Q \"" + stringReplace(filedir(B.name),"/","\\") + "window.png\"";
			//cmd += " & pause";
			//dlgMessageBox(stringFromInt(exp_window));
			system(cmd);
		}
	}
}
