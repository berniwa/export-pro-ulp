/**
 * This ULP generates a CSV BOM
 *
 * @author 		Bernhard Wörndl-Aichriedler <bwa@xdevelop.at>
 * @copyright	2016-2019, Bernhard Wörndl-Aichriedler
 * @license 	BSD-3-Clause
 */

string bomCsvSafe(string str) {
  str = stringReplace(str, "\"", "\\\"");

  return str;
}


void bomOutputCsvFile(string ofilename) {
  output(ofilename) {
    printf("\"Lfd. Nr.\";\"Stueckzahl\";\"Benennung\";\"Referenzkennzeichen\";\"Lieferant\";\"Bestellnummer\";\"RoHS\";\"Preis / VE\";\"VE\";\"Bemerkung\";\r");
    for(int i = 0; i < bomInfoCount; i++) {
      printf("\"%d\";\"%d\";\"%s\";\"%s\";\"%s\";\"%s\";\"J\";\"%s\";\"%s\";\"%s\";\r"
      ,i+1, bomInfoPartCount[i], bomCsvSafe(bomOutputName[i]), bomCsvSafe(bomOutputParts[i]), bomXMLSafe(bomAttributeDistributor[i]), bomXMLSafe(bomAttributeOrderNo[i]),bomXMLSafe(stringConvertDotToComma(bomAttributePrice[i])), bomXMLSafe(bomAttributePartsPerPackage[i]),  bomCsvSafe(bomOutputNote[i]));
    }   
  } 
}
