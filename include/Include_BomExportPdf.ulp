/**
 * This ULP generates the embedded pdf BOM
 *
 * @author 		Tobias Hofer <thofer@xdevelop.at>
 * @author 		Bernhard Wörndl-Aichriedler <bwa@xdevelop.at>
 * @copyright	2019, Bernhard Wörndl-Aichriedler
 * @license 	BSD-3-Clause
 */


#include "Include_FastExecute.ulp";
#include "Include_Config.ulp";

real startX=0, startY=0;
string LIBRARY_NAME = "fabrication.lbr";
string BOARD_NAME = ".brd";
string cols="1;1;1;1;1;1;1";

string newRow="";

real 	frameWith			= 0.5;		//in mm
real 	rowHeight 			= 2.5; 		//in mm
int 	headHight 			= 51;		//in mm
string 	outputLayerName 	= "FabDoc3";	//in mm
int 	outputLayer 		= lay_fabDoc[2];		//in mm
real 	lineWidth 			= 0.1016;	//in mm
real 	textSize 			= 1.778;	//in mm
real 	lineWidthBorder		= 0.2032; 	//in mm
real 	distance  			= 0.5;		//in mm, from left cell edge
int 	ratioNormal 		= 8;		//
int 	ratioHeadline		= 12;		//
real 	charWidth			= 1.64;		//in mm

int 	spaceID				= 3;		//in %
int 	spacePartNr			= 3;		//in %
int 	spaceName			= 14;		//in %
int 	spaceDesinator		= 22;		//in %
int 	spaceManufacturer	= 22;		//in %
int 	spaceMPN			= 24;		//in %
int 	spacePackage		= 7;		//in %
int 	spacePop			= 5;		//in %
						//+ =100

char replace = 0;

void initVariables(real offsetX, real offsetY, real width) {
	board(B){
		BOARD_NAME = B.name;
		LIBRARY_NAME = filedir(BOARD_NAME)+LIBRARY_NAME;
		B.elements(E) {
			if (strstr(E.package.name,"FRAME")!=-1){
				E.package.wires(W){
					if(startX > u2mm(W.x1)){
						startX = u2mm(W.x1);
					}
					if(startX > u2mm(W.x2)){
						startX = u2mm(W.x2);
					}
					if(startY < u2mm(W.y1)){
						startY = u2mm(W.y1);
					}
					if(startY < u2mm(W.y2)){
						startY = u2mm(W.y2);
					}
				}
			}

			if(E.name == "BOM"){
				replace = 1;
			}
		}
	}

	startX+=offsetX;
	startY-=offsetY;

	sprintf(cols,"%f;%f;%f;%f;%f;%f;%f;%f",
		width*(real(spaceID)/100),
		width*(real(spacePartNr)/100),
		width*(real(spaceName)/100),
		width*(real(spaceDesinator)/100),
		width*(real(spaceManufacturer)/100),
		width*(real(spaceMPN)/100),
		width*(real(spacePackage)/100),
		width*(real(spacePop)/100)
	);
}

real getTotalWidth(string cols) {
	real width = 0.0;
	//Walk through all columns
	string buffer = "";
	for(int i = 0; cols[i]; i++) {
		if(cols[i] == ';'){
			width += strtod(buffer);
			buffer = "";
		} else {
			buffer = buffer + cols[i];
		}
	}
	width += strtod(buffer);
	return width;
}

/**
 * Draw a row of table
 */
string drawRow(real startx, real starty, int row, int isHeadline, int align, string cols, string text) {
	//Column widths
	real 	widths[];
	string 	texts[];

	//Walk through column content
	string buffer = "";
	int index = 0;
	for(int i = 0; text[i]; i++) {
		if(text[i] == ';'){
			texts[index++] = buffer;
			buffer = "";
		} else {
			buffer = buffer + text[i];
		}
	}
	texts[index++] = buffer;

	//Walk through all columns
	index = 0;
	buffer = "";
	for(i = 0; cols[i]; i++) {
		if(cols[i] == ';'){
			widths[index++] = strtod(buffer);
			buffer = "";
		} else {
			buffer = buffer + cols[i];
		}
	}
	widths[index++] = strtod(buffer);

	//Draw columns and 
	string cmd = "";
	real x = startx;
	real y = starty - row*rowHeight;

	sprintf(cmd, "%sCHANGE RATIO %d;\n", cmd, isHeadline?ratioHeadline:ratioNormal);
	for(i = 0; i < index; i++){
		sprintf(cmd, "%sWIRE (%f %f) (%f %f) (%f %f);\n", cmd,
				x, 				y-rowHeight, 
				x, 				y, 
				x+widths[i], 	y
		);

		if(widths[i]<(real(strlen(texts[i]))*charWidth)){
			if(i==3){//designator
				string tmp[],this[],next[];
				int c=0;
				int leangth=0;
				int d = strsplit(tmp,texts[i],',');
				for(int n=0; n<d; n++){
					if((c==0) && (widths[i]<(real(leangth+strlen(tmp[n])+n)*charWidth))) {
						c=n;
					}
					else{
						leangth += strlen(tmp[n]);
					}

					if(c==0) {
						this[n]=tmp[n];
					}
					else {
						next[n-c]=tmp[n];
					}
				}

				texts[i] = strjoin(this,',')+",";
				newRow = strjoin(next,','); 
			}
			else{
				texts[i] = strsub(texts[i],0,(int(widths[i]/charWidth)-2));
				texts[i] += "...";
			}
		}

		real x2 = 0.0;
		if(align == 0){
			sprintf(cmd, "%sCHANGE ALIGN CENTER LEFT;\n", cmd);
			x2 = x+distance;
		} else if(align == 1) {
			sprintf(cmd, "%sCHANGE ALIGN CENTER CENTER;\n", cmd);
			x2 = x+(widths[i]/2);
		}
		sprintf(cmd, "%sTEXT '%s' (%f %f);\n", cmd, texts[i], x2, y-(rowHeight/2));
		x =  x + widths[i];

		if(isHeadline == 2 && i == 0) {
			sprintf(cmd, "%sCHANGE RATIO %d;\n", cmd, ratioNormal);
		}
	}
	sprintf(cmd, "%sWIRE (%f %f) (%f %f) (%f %f);\n", cmd, 
		x, y, x, y-rowHeight, startx, y-rowHeight);

	return cmd;
}

/**
 * Draw the border of the table
 */
string drawBorder(real startx, real starty, int rows, string cols) {
	string cmd = "";

	real width = getTotalWidth(cols);
	sprintf(cmd, "%sCHANGE WIDTH %fmm;\n", cmd, lineWidthBorder);
	sprintf(cmd, "%sWIRE (%f %f) (%f %f) (%f %f) (%f %f) (%f %f);\n", cmd, 
		startx, 		starty, 
		startx+width, 	starty, 
		startx+width, 	starty-rows*rowHeight, 
		startx, 		starty-rows*rowHeight,
		startx, 		starty
	);	
	sprintf(cmd, "%sCHANGE WIDTH %fmm;\n", cmd, lineWidth);
	return cmd;
}

void bomOutputPdfFile(real offsetX, real offsetY, real width){

	string cmd = "";
	initVariables(offsetX, offsetY, width);

	cmd += "OPEN \'"+LIBRARY_NAME+"\';\n";
	cmd += "SET CONFIRM YES;\n";
	cmd += "EDIT bom.pac;\n";
	sprintf(cmd, "%sLAYER %s %d;\n", cmd, outputLayerName, outputLayer);
	sprintf(cmd, "%sCHANGE LAYER %d;\n", cmd, outputLayer);
	sprintf(cmd, "%sCHANGE WIDTH %fmm;\n", cmd, lineWidth);
	sprintf(cmd, "%sCHANGE SIZE %fmm;\n", cmd, textSize);
	cmd += "CHANGE ALIGN TOP LEFT;\n";
	cmd += "CHANGE FONT VECTOR;\n";
	cmd += "GRID mm 0.1;\n";
	cmd += "SET WIRE_BEND 2;\n";

	cmd+="GROUP ALL;\n";
	cmd+="DELETE (>0 0);\n";

	int row = 0;
	string buffer;

	cmd += drawRow(0, 0, row++, 1, 1, cols, "ID;CNT;TYPE;DESIGNATOR;MANUFACTURER;MPN;PACKAGE;POP");

	for(int i = 0; i < bomInfoCount; i++) {
      	sprintf(buffer,"%d;%d;%s;%s;%s;%s;%s;%s",
        	i+1, 
        	bomInfoPartCount[i], 
        	bomOutputName[i], 
        	bomOutputParts[i],
        	bomAttributeManufacturer[i], 
        	bomAttributePartNo[i], 
        	bomInfoPackage[i],
        	bomAttributePopulate[i]
       	);
       	newRow="";
		cmd += drawRow(0, 0, row++, 0, 0, cols, buffer);
       	
       	while(newRow!=""){
       		sprintf(buffer,";;;%s;;;;", newRow);
       		newRow="";
       		cmd += drawRow(0, 0, row++, 0, 0, cols, buffer);
       	}
    }
    cmd += drawBorder(0, 0, row, cols);

    sprintf(cmd, "%sWRITE '%s';\n", cmd, LIBRARY_NAME);
	sprintf(cmd, "%sCLOSE;\n", cmd);
	sprintf(cmd, "%sEDIT '%s';\n", cmd, BOARD_NAME);
	sprintf(cmd, "%sGRID mm 0.1 1 mm;\n", cmd);
	sprintf(cmd, "%sUSE '%s';\n", cmd, LIBRARY_NAME);
	sprintf(cmd, "%sLAYER %s %d;\n", cmd, outputLayerName, outputLayer);

	if(replace) {
		cmd += "DELETE BOM;\n";
	}

	sprintf(cmd, "%sADD 'bom@%s' BOM R0 (%.3f %.3f);\n", cmd,
		LIBRARY_NAME, 
 		startX, startY
 	);

	executeAndExit(cmd);
}
