/**
 * This ULP will handle the SI units and unit conversion
 *
 * @author 		Bernhard Wörndl-Aichriedler <bwa@xdevelop.at>
 * @copyright	2016-2019, Bernhard Wörndl-Aichriedler
 * @license 	BSD-3-Clause
 */

/* SI_VALUE_DEFINITION */
char 	SI_NAMES[]	= {'R', 'F', 'H', 'f', 'p', 'n', 'u', 'µ', 'm', 'k', 'K', 'M', 'G', 'T'};
int		SI_VALUE[]	= { 0 ,  0 ,  0 , -15, -12,  -9,  -6,  -6,  -3,  3 ,  3 ,  6 ,  9 ,  12};


int siGetIndex(char c)
{
	for(int i = 0; SI_NAMES[i]; i++)
	{
		if(SI_NAMES[i] == c)
		{
			return i;
		}
	}

	return -1;	
}

real siParseValue(string value)
{
	value = stringTrim(value);

	string tmpvalue = "";
	real multiplier = 1;
	real rdata = 0;


	for (int i = 0; value[i]; ++i) 
	{
		if(value[i] >= '0' && value[i] <= '9' || value[i] == '.') //ASCII TABLE Comparison - 0123456789 <-
		{
			tmpvalue += value[i];
		}
		else if(siGetIndex(value[i]) != -1)
		{
			tmpvalue += ".";
			if(multiplier == 1) // If another multi was set: example 2k2R <-- Wrong but recognised correct
			{
				multiplier = pow(10,SI_VALUE[siGetIndex(value[i])]);
			}
		}
		else
		{
			break;
		}
	}

	rdata = strtod(tmpvalue);
	rdata *= multiplier;

	return rdata;
}
