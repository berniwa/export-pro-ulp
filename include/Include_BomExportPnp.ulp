/**
 * This ULP generates a pnp BOM, that is eurocircuits compatible
 *
 * @author    Bernhard Wörndl-Aichriedler <bwa@xdevelop.at>
 * @copyright 2009-2019, Bernhard Wörndl-Aichriedler
 * @license   BSD-3-Clause
 */

void bomOutputPnpFile(string ofilename)
{
  output(ofilename)
  {
    printf("ID,COUNT,DESIGNATOR,VALUE,MANUFACTURER,MPN,SUPPLIER,SPN,POPULATE,PACKAGE,URL\n");
    for(int i = 0; i < bomInfoCount; i++)
    {
      string populate = "YES";
      if(strlen(bomAttributePopulate[i]) > 0){
        populate = bomCsvSafe(bomAttributePopulate[i]);
      }

      printf("%d,%d,\"%s\",\"%s\",\"%s\",\"%s\",\"%s\",\"%s\",\"%s\",\"%s\",\"%s\"\n"
        ,i+1, bomInfoPartCount[i], bomCsvSafe(bomOutputParts[i]), 
        bomCsvSafe(bomInfoValue[i]), 
        bomCsvSafe(bomAttributeManufacturer[i]), bomCsvSafe(bomAttributePartNo[i]), 
        bomCsvSafe(bomAttributeDistributor[i]), bomCsvSafe(bomAttributeOrderNo[i]),
        populate, bomCsvSafe(bomInfoPackage[i]), bomCsvSafe(bomAttributeDatasheet[i])
      );
    }   
  } 
}
