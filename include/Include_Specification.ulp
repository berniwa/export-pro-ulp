/**
 * This ULP will write a simple specficaition file, 
 * containing the board details
 *
 * @author 		Bernhard Wörndl-Aichriedler <bwa@xdevelop.at>
 * @copyright	2013-2019, Bernhard Wörndl-Aichriedler
 * @license 	BSD-3-Clause
 */
#usage ""

output(argv[1], "wt") {
	printf("PC board specifications: \n");
	printf("Board thickness:   	%s\n", 		argv[2]);
	printf("Board type:       	%s\n", 		argv[3]);
	printf("Number of layers:  	%s\n", 		argv[4]);
	printf("End copper thickness:	%s\n", 		argv[5]);
	printf("Stop mask color:   	%s\n", 		argv[6]);
	printf("Silk screen color: 	%s\n", 		argv[7]);
	printf("Surface finish:    	%s\n", 		argv[8]);
	printf("Silk screen trim: 	Trim on solder mask opening pads\n");
	
	if(argc > 9)
	{
		printf("\n");
		printf("Top silkscreen layers:    %s\n", 	argv[9]);
		printf("Bottom silkscreen layers: %s\n", 	argv[10]);
	}
}
