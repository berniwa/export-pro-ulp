/**
 * This ULP generates XML bom from MS excel
 *
 * @author    Bernhard Wörndl-Aichriedler <bwa@xdevelop.at>
 * @copyright 2009-2019, Bernhard Wörndl-Aichriedler
 * @license   BSD-3-Clause
 */

string bomXMLSafe(string str)
{
	str = stringReplace(str, "&", "&amp;");
	str = stringReplace(str, "\"", "&quot;");	
	str = stringReplace(str, "'", "&#039;");
	str = stringReplace(str, "<", "&lt;");	
	str = stringReplace(str, ">", "&gt;");

	return str;
}

void bomOutputXslFile(string ofilename)
{
	output(ofilename)
	{
		printf("\
			<?xml version=\"1.0\" ?> \n\
			<?mso-application progid=\"Excel.Sheet\"?> \n\
			<Workbook xmlns=\"urn:schemas-microsoft-com:office:spreadsheet\" xmlns:ss=\"urn:schemas-microsoft-com:office:spreadsheet\">\n\
        <ss:Styles>\n\
            <ss:Style ss:ID=\"HEAD\">\n\
                <ss:Font ss:Bold=\"1\"/>\n\
                <Borders>\n\
                  <Border ss:Position=\"Bottom\" ss:LineStyle=\"Continuous\" ss:Weight=\"1\"/>\n\
                </Borders>\n\
            </ss:Style>\n\
            <ss:Style ss:ID=\"SIDE\">\n\
                <ss:Font ss:Bold=\"1\"/>\n\
                <Borders>\n\
                  <Border ss:Position=\"Right\" ss:LineStyle=\"Continuous\" ss:Weight=\"1\"/>\n\
                </Borders>\n\
            </ss:Style>\n\
        </ss:Styles>\n\
			 	<Worksheet ss:Name=\"Parts\">\n\
					<Table>\n\
            <ss:Column ss:Width=\"30\"/>\n\
            <ss:Column ss:Width=\"30\"/>\n\
            <ss:Column ss:Width=\"100\"/>\n\
            <ss:Column ss:Width=\"100\"/>\n\
            <ss:Column ss:Width=\"100\"/>\n\
            <ss:Column ss:Width=\"100\"/>\n\
            <ss:Column ss:Width=\"100\"/>\n\
            <ss:Column ss:Width=\"100\"/>\n\
            <ss:Column ss:Width=\"50\"/>\n\
            <ss:Column ss:Width=\"50\"/>\n\
            <ss:Column ss:Width=\"50\"/>\n\
            <ss:Column ss:Width=\"100\"/>\n\
            <ss:Column ss:Width=\"300\"/>\n\
		");

		

		printf("\
			     <Row> \n\
        				<Cell ss:Index=\"1\" ss:StyleID=\"HEAD\">\n\
          				<Data ss:Type=\"String\">No.</Data>\n\
        				</Cell>\n\
        				<Cell ss:Index=\"2\" ss:StyleID=\"HEAD\">\n\
          				<Data ss:Type=\"String\">Count</Data>\n\
        				</Cell>\n\
        				<Cell ss:Index=\"3\" ss:StyleID=\"HEAD\">\n\
          				<Data ss:Type=\"String\">Type</Data>\n\
        				</Cell>\n\
        				<Cell ss:Index=\"4\" ss:StyleID=\"HEAD\">\n\
          				<Data ss:Type=\"String\">Name</Data>\n\
        				</Cell>\n\
        				<Cell ss:Index=\"5\" ss:StyleID=\"HEAD\">\n\
          				<Data ss:Type=\"String\">Distributor</Data>\n\
        				</Cell>\n\
        				<Cell ss:Index=\"6\" ss:StyleID=\"HEAD\">\n\
          				<Data ss:Type=\"String\">Order No.</Data>\n\
        				</Cell>\n\
        				<Cell ss:StyleID=\"HEAD\">\n\
     					    <Data ss:Type=\"String\">Manufacturer</Data>\n\
        				</Cell>\n\
        				<Cell ss:StyleID=\"HEAD\">\n\
     					    <Data ss:Type=\"String\">Part No.</Data>\n\
        				</Cell>\n\
        				<Cell ss:StyleID=\"HEAD\">\n\
          				<Data ss:Type=\"String\">Price / Package</Data>\n\
        				</Cell>\n\
        				<Cell ss:StyleID=\"HEAD\">\n\
          				<Data ss:Type=\"String\">Package</Data>\n\
        				</Cell>\n\
        				<Cell ss:StyleID=\"HEAD\">\n\
     					    <Data ss:Type=\"String\">Case</Data>\n\
        				</Cell>\n\
        				<Cell ss:StyleID=\"HEAD\">\n\
     					    <Data ss:Type=\"String\">Populate</Data>\n\
        				</Cell>\n\
                <Cell ss:StyleID=\"HEAD\">\n\
                  <Data ss:Type=\"String\">Note</Data>\n\
                </Cell>\n\
      			</Row>\n\
		");
		
		for(int i = 0; i < bomInfoCount; i++)
		{
			printf("\
			<Row> \n\
        				<Cell ss:Index=\"1\" ss:StyleID=\"SIDE\">\n\
          				<Data ss:Type=\"Number\">%d</Data>\n\
        				</Cell>\n\
        				<Cell ss:Index=\"2\">\n\
          				<Data ss:Type=\"Number\">%d</Data>\n\
        				</Cell>\n\
        				<Cell ss:Index=\"3\">\n\
          				<Data ss:Type=\"String\">%s</Data>\n\
        				</Cell>\n\
        				<Cell ss:Index=\"4\">\n\
          				<Data ss:Type=\"String\">%s</Data>\n\
        				</Cell>\n\
        				<Cell ss:Index=\"5\">\n\
          				<Data ss:Type=\"String\">%s</Data>\n\
        				</Cell>\n\
        				<Cell ss:Index=\"6\">\n\
          				<Data ss:Type=\"String\">%s</Data>\n\
        				</Cell>\n\
        				<Cell>\n\
     					    <Data ss:Type=\"String\">%s</Data>\n\
        				</Cell>\n\
        				<Cell>\n\
     					    <Data ss:Type=\"String\">%s</Data>\n\
        				</Cell>\n\
        				<Cell>\n\
          				<Data ss:Type=\"Number\">%s</Data>\n\
        				</Cell>\n\
        				<Cell>\n\
          				<Data ss:Type=\"Number\">%s</Data>\n\
        				</Cell>\n\
        				<Cell>\n\
     					    <Data ss:Type=\"String\">%s</Data>\n\
        				</Cell>\n\
        				<Cell>\n\
     					    <Data ss:Type=\"String\">%s</Data>\n\
        				</Cell>\n\
                <Cell>\n\
                  <Data ss:Type=\"String\">%s</Data>\n\
                </Cell>\n\
      			</Row>\n\
			",i+1, bomInfoPartCount[i], bomXMLSafe(bomOutputName[i]), bomXMLSafe(bomOutputParts[i]),
			bomXMLSafe(bomAttributeDistributor[i]), bomXMLSafe(bomAttributeOrderNo[i]),
			 bomXMLSafe(bomAttributeManufacturer[i]), 
			bomXMLSafe(bomAttributePartNo[i]), 
			bomXMLSafe(stringConvertDotToComma(bomAttributePrice[i])), bomXMLSafe(bomAttributePartsPerPackage[i]),
			bomXMLSafe(bomOutputNote[i]),
			bomXMLSafe(bomAttributePopulate[i]),      
      bomXMLSafe(bomAttributeNote[i]) 	
			);			
		}

		printf("\
				</Table>\n\
  			</Worksheet>\n\
			<Worksheet ss:Name=\"HTL\">\n\
				<Table>\n\
		");

		printf("\
			<Row> \n\
        				<Cell ss:Index=\"1\">\n\
          				<Data ss:Type=\"String\">Lfd. Nr.</Data>\n\
        				</Cell>\n\
        				<Cell ss:Index=\"2\">\n\
          				<Data ss:Type=\"String\">Stueckzahl</Data>\n\
        				</Cell>\n\
        				<Cell ss:Index=\"3\">\n\
          				<Data ss:Type=\"String\">Benennung</Data>\n\
        				</Cell>\n\
        				<Cell ss:Index=\"4\">\n\
          				<Data ss:Type=\"String\">Referenzkennzeichen</Data>\n\
        				</Cell>\n\
        				<Cell ss:Index=\"5\">\n\
          				<Data ss:Type=\"String\">Lieferant</Data>\n\
        				</Cell>\n\
        				<Cell ss:Index=\"6\">\n\
          				<Data ss:Type=\"String\">Bestellnummer</Data>\n\
        				</Cell>\n\
        				<Cell ss:Index=\"7\">\n\
          				<Data ss:Type=\"String\">RoHS</Data>\n\
        				</Cell>\n\
        				<Cell ss:Index=\"8\">\n\
          				<Data ss:Type=\"String\">Preis / VE</Data>\n\
        				</Cell>\n\
        				<Cell ss:Index=\"9\">\n\
          				<Data ss:Type=\"String\">VE</Data>\n\
        				</Cell>\n\
        				<Cell ss:Index=\"10\">\n\
     					<Data ss:Type=\"String\">Bemerkung</Data>\n\
        				</Cell>\n\
      			</Row>\n\
		");



		for(i = 0; i < bomInfoCount; i++)
		{
			printf("\
			<Row> \n\
        				<Cell ss:Index=\"1\">\n\
          				<Data ss:Type=\"Number\">%d</Data>\n\
        				</Cell>\n\
        				<Cell ss:Index=\"2\">\n\
          				<Data ss:Type=\"Number\">%d</Data>\n\
        				</Cell>\n\
        				<Cell ss:Index=\"3\">\n\
          				<Data ss:Type=\"String\">%s</Data>\n\
        				</Cell>\n\
        				<Cell ss:Index=\"4\">\n\
          				<Data ss:Type=\"String\">%s</Data>\n\
        				</Cell>\n\
        				<Cell ss:Index=\"5\">\n\
          				<Data ss:Type=\"String\">%s</Data>\n\
        				</Cell>\n\
        				<Cell ss:Index=\"6\">\n\
          				<Data ss:Type=\"String\">%s</Data>\n\
        				</Cell>\n\
        				<Cell ss:Index=\"7\">\n\
          				<Data ss:Type=\"String\">J</Data>\n\
        				</Cell>\n\
        				<Cell ss:Index=\"8\">\n\
          				<Data ss:Type=\"Number\">%s</Data>\n\
        				</Cell>\n\
        				<Cell ss:Index=\"9\">\n\
          				<Data ss:Type=\"Number\">%s</Data>\n\
        				</Cell>\n\
        				<Cell ss:Index=\"10\">\n\
     					<Data ss:Type=\"String\">%s</Data>\n\
        				</Cell>\n\
      			</Row>\n\
			",i+1, bomInfoPartCount[i], bomXMLSafe(bomOutputName[i]), bomXMLSafe(bomOutputParts[i]), 
				bomXMLSafe(bomAttributeDistributor[i]), bomXMLSafe(bomAttributeOrderNo[i]), bomXMLSafe(stringConvertDotToComma(bomAttributePrice[i])), bomXMLSafe(bomAttributePartsPerPackage[i]), bomXMLSafe(bomOutputNote[i]));			
		}
			

		printf("\
				</Table>\n\
  			</Worksheet>\n\
			<Worksheet ss:Name=\"Advanced\">\n\
				<Table>\n\
		");

		printf("\
			<Row> \n\
        				<Cell ss:Index=\"1\">\n\
          				<Data ss:Type=\"String\">Lfd. Nr.</Data>\n\
        				</Cell>\n\
        				<Cell ss:Index=\"2\">\n\
          				<Data ss:Type=\"String\">Stueckzahl</Data>\n\
        				</Cell>\n\
        				<Cell ss:Index=\"3\">\n\
          				<Data ss:Type=\"String\">Benennung</Data>\n\
        				</Cell>\n\
        				<Cell ss:Index=\"4\">\n\
          				<Data ss:Type=\"String\">Referenzkennzeichen</Data>\n\
        				</Cell>\n\
        				<Cell ss:Index=\"5\">\n\
          				<Data ss:Type=\"String\">Lieferant</Data>\n\
        				</Cell>\n\
        				<Cell ss:Index=\"6\">\n\
          				<Data ss:Type=\"String\">Bestellnummer</Data>\n\
        				</Cell>\n\
        				<Cell>\n\
     					<Data ss:Type=\"String\">Hersteller</Data>\n\
        				</Cell>\n\
        				<Cell>\n\
     					<Data ss:Type=\"String\">Teilnummer</Data>\n\
        				</Cell>\n\
        				<Cell>\n\
     					<Data ss:Type=\"String\">Referenznummer</Data>\n\
        				</Cell>\n\
        				<Cell>\n\
     					<Data ss:Type=\"String\">Frei 1</Data>\n\
        				</Cell>\n\
        				<Cell>\n\
     					<Data ss:Type=\"String\">Frei 2</Data>\n\
        				</Cell>\n\
        				<Cell>\n\
          				<Data ss:Type=\"String\">RoHS</Data>\n\
        				</Cell>\n\
        				<Cell>\n\
          				<Data ss:Type=\"String\">Preis / VE</Data>\n\
        				</Cell>\n\
        				<Cell>\n\
          				<Data ss:Type=\"String\">VE</Data>\n\
        				</Cell>\n\
        				<Cell >\n\
     					<Data ss:Type=\"String\">Bemerkung</Data>\n\
        				</Cell>\n\
        				<Cell>\n\
     					<Data ss:Type=\"String\">GP1</Data>\n\
        				</Cell>\n\
        				<Cell>\n\
     					<Data ss:Type=\"String\">GP2</Data>\n\
        				</Cell>\n\
        				<Cell>\n\
     					<Data ss:Type=\"String\">GP3</Data>\n\
        				</Cell>\n\
        				<Cell>\n\
     					<Data ss:Type=\"String\">GP4</Data>\n\
        				</Cell>\n\
        				<Cell>\n\
     					<Data ss:Type=\"String\">Part ID</Data>\n\
        				</Cell>\n\
        				<Cell>\n\
     					<Data ss:Type=\"String\">Parsed Value</Data>\n\
        				</Cell>\n\
        				<Cell>\n\
     					<Data ss:Type=\"String\">Package</Data>\n\
        				</Cell>\n\
        				<Cell>\n\
     					<Data ss:Type=\"String\">Device</Data>\n\
        				</Cell>\n\
        				<Cell>\n\
     					<Data ss:Type=\"String\">Description</Data>\n\
        				</Cell>\n\
      			</Row>\n\
		");
		
		for(i = 0; i < bomInfoCount; i++)
		{
			printf("\
			<Row> \n\
        				<Cell ss:Index=\"1\">\n\
          				<Data ss:Type=\"Number\">%d</Data>\n\
        				</Cell>\n\
        				<Cell ss:Index=\"2\">\n\
          				<Data ss:Type=\"Number\">%d</Data>\n\
        				</Cell>\n\
        				<Cell ss:Index=\"3\">\n\
          				<Data ss:Type=\"String\">%s</Data>\n\
        				</Cell>\n\
        				<Cell ss:Index=\"4\">\n\
          				<Data ss:Type=\"String\">%s</Data>\n\
        				</Cell>\n\
        				<Cell ss:Index=\"5\">\n\
          				<Data ss:Type=\"String\">%s</Data>\n\
        				</Cell>\n\
        				<Cell ss:Index=\"6\">\n\
          				<Data ss:Type=\"String\">%s</Data>\n\
        				</Cell>\n\
        				<Cell>\n\
     					<Data ss:Type=\"String\">%s</Data>\n\
        				</Cell>\n\
        				<Cell>\n\
     					<Data ss:Type=\"String\">%s</Data>\n\
        				</Cell>\n\
        				<Cell>\n\
     					<Data ss:Type=\"String\">%s</Data>\n\
        				</Cell>\n\
        				<Cell>\n\
     					<Data ss:Type=\"String\">%s</Data>\n\
        				</Cell>\n\
        				<Cell>\n\
     					<Data ss:Type=\"String\">%s</Data>\n\
        				</Cell>\n\
        				<Cell>\n\
          				<Data ss:Type=\"String\">J</Data>\n\
        				</Cell>\n\
        				<Cell>\n\
          				<Data ss:Type=\"Number\">%s</Data>\n\
        				</Cell>\n\
        				<Cell>\n\
          				<Data ss:Type=\"Number\">%s</Data>\n\
        				</Cell>\n\
        				<Cell>\n\
     					<Data ss:Type=\"String\">%s</Data>\n\
        				</Cell>\n\
				<Cell>\n\
     					<Data ss:Type=\"String\">%s</Data>\n\
        				</Cell>\n\
        				<Cell>\n\
     					<Data ss:Type=\"String\">%s</Data>\n\
        				</Cell>\n\
        				<Cell>\n\
     					<Data ss:Type=\"String\">%s</Data>\n\
        				</Cell>\n\
        				<Cell>\n\
     					<Data ss:Type=\"String\">%s</Data>\n\
        				</Cell>\n\
        				<Cell>\n\
     					<Data ss:Type=\"Number\">%d</Data>\n\
        				</Cell>\n\
        				<Cell>\n\
     					<Data ss:Type=\"Number\">%s</Data>\n\
        				</Cell>\n\
        				<Cell>\n\
     					<Data ss:Type=\"String\">%s</Data>\n\
        				</Cell>\n\
        				<Cell>\n\
     					<Data ss:Type=\"String\">%s</Data>\n\
        				</Cell>\n\
        				<Cell>\n\
     					<Data ss:Type=\"String\">%s</Data>\n\
        				</Cell>\n\
      			</Row>\n\
			",i+1, bomInfoPartCount[i], bomXMLSafe(bomOutputName[i]), bomXMLSafe(bomOutputParts[i]),
			bomXMLSafe(bomAttributeDistributor[i]), bomXMLSafe(bomAttributeOrderNo[i]),
			 bomXMLSafe(bomAttributeManufacturer[i]), 
			bomXMLSafe(bomAttributePartNo[i]), bomXMLSafe(bomAttributeReferenceNo[i]), bomXMLSafe(bomAttributeReserved1[i]),  
			bomXMLSafe(bomAttributeReserved2[i]), 
			bomXMLSafe(stringConvertDotToComma(bomAttributePrice[i])), bomXMLSafe(bomAttributePartsPerPackage[i]),
			 bomXMLSafe(bomOutputNote[i]), 
			bomXMLSafe(bomOutputGP1[i]), bomXMLSafe(bomOutputGP2[i]), bomXMLSafe(bomOutputGP3[i]), bomXMLSafe(bomOutputGP4[i]),
			bomInfoPartId[i], bomXMLSafe(stringFromReal(bomInfoParsedValue[i])), bomXMLSafe(bomInfoPackage[i]), 
			bomXMLSafe(bomInfoDevice[i]),bomXMLSafe(bomInfoDescription[i])			
			);			
		}		

		printf("\
				</Table>\n\
  			</Worksheet>\n\
			</Workbook>\n\
		");

	}	

}
