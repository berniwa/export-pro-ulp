/**
 * This ULP exports basic eurocircuits compatible pick and place data
 *
 * Note: Some parts of this ULP have been taken from the Charmhigh ULP 
 *       (Nathan Seidle)
 * 
 * @author    Bernhard Wörndl-Aichriedler <bwa@xdevelop.at>
 * @author    Tobias Hofer <thofer@xdevelop.at>
 * @author    Nathan Seidle <nathan@sparkfun.com>
 * @copyright 2009-2019, Bernhard Wörndl-Aichriedler
 * @license   BSD-3-Clause
 */

//Config options we want to save
real      offsetY             = 0.0; 
real      offsetX             = 0.0;
int       enableTop           = 1;
int       enableBottom        = 1;
int       useAutomaticOffset  = 1;
int       flip                = 0;

string pnpName[];
string pnpDesignator[];
int    pnpX[];
int    pnpY[];
real   pnpAngle[];
int    pnpFeeder[];
int    pnpPos[];    //Top or bottom
int    pnpType[];
int    pnpCount;    
int    pnpStatsPartsTotal;
int    pnpStatsPartsOk;
int    pnpStatsPartsNew;
int    pnpStatsPartsDnp;
int    pnpStatsPartsError;
string pnpBasefile;

int maxX        = 0;
int minX        = 0;
int maxY        = 0;
int minY        = 0;
int initialized = 0;
real originX    = 0;
real originY    = 0;
real widthX     = 0;
real widthY     = 0;

int MAX_FEEDER    		= 99;
int FEEDER_FIDUCIAL   = 1000;
int FEEDER_NEW    		= -1;
int FEEDER_DNP    		= 0;
int FEEDER_NO_MOUNT    	= 30; //This comes from spreadsheet

/**
 * This function transforms the X coordinates
 * according to the settings
 * @return Transformed X coordinate
 */
int transformCoordinateX(int x, int pos){
  //Pre default, use the automatically generated coordinates
  int oX = minX;
  int wX = maxX;

  //If this causes problems, we allow overwriting the automatic 
  //offset with manual information
  if(!useAutomaticOffset){
    oX = mm2u(originX);
    wX = mm2u(widthX);
  }

  //Handle Top + Bottom H/V Flip transformation
  int offset = 0;
  if(pos == 0){
    offset = x - oX;
  } else {
    if(flip == 1){
      offset = wX - x;
    } 
    if(flip == 2){
      offset = x - oX;
    }
    else {  
      offset = x;    
    }
  }
  return offset + mm2u(offsetX);
}

/**
 * This function transforms the Y coordinates
 * according to the settings
 * @return Transformed X coordinate
 */
int transformCoordinateY(int y, int pos){
  //Pre default, use the automatically generated coordinates
  int oY = minY;
  int wY = maxY;

  //If this causes problems, we allow overwriting the automatic 
  //offset with manual information
  if(!useAutomaticOffset){
    oY = mm2u(originY);
    wY = mm2u(widthY);
  }

  //Handle Top + Bottom H/V Flip transformation
  int offset = 0;
  if(pos == 0){
    offset = y - oY;
  } else {
    if(flip == 1){
      offset = y - oY;
    } 
    if(flip == 2){
      offset = wY - y;
    }
    else {  
      offset = y;    
    }


  }
  return offset + mm2u(offsetY);
}

/**
 * Adds the opening header information to the dpv file
 */
void addHeader()
{
  //File header
  printf("ID, PART, SIDE, TYPE, X, Y, ROTATION\n");
}

int componentID = 0;

/**
 * Add all the components to the output file
 * @param   position      Top (0) or bottom (1) layer placement
 */
void addComponents(int position)
{
  string pos = "TOP";
  if(position == 1){
    pos = "BOTTOM";
  }

  for(int i = 0; i < pnpCount; i++){
    if(pnpPos[i] == position){

      string type = "TH";
      if(pnpType[i] == 1){
        type = "SMD";
      }


      printf("%d, %s, %s, %s, %.3f, %.3f, %.3f\n",
             componentID, pnpDesignator[i], pos, type,
             u2mm(transformCoordinateX(pnpX[i], pnpPos[i])), 
             u2mm(transformCoordinateY(pnpY[i], pnpPos[i])), 
             pnpAngle[i]); 

      componentID++;
    }
  }
}

/** 
 * Process all information and create the output file
 */
void writeOutputFile(string fname, int top, int bottom) 
{
  output(fname)
  {
    addHeader(); 
    if(top){
      addComponents(0); 
    }
    if(bottom){
      addComponents(1);
    }
  }  
}

/**
 * Process the coordinates to determine min/max of the outline
 * param  x   X coordinate of the current element
 * param  Y   Y coordinate of the current element
 */
void setCoordinates(int x, int y)
{
  if(!initialized) {
    maxX = x;
    minX = x;
    maxY = y;
    minY = y;
    initialized = 1;
  }

  if(x < minX) {
    minX = x;
  }
  if(y < minY) {
    minY = y;
  }
  if(y > maxY) {
    maxY = y;  
  }
  if(x > maxX) {
    maxX = x;  
  }
}

/**
 * Load all required information from the board
 */
void loadBoardInformation() {
  pnpCount            = 0;
  pnpStatsPartsTotal  = 0;
  pnpStatsPartsOk     = 0;
  pnpStatsPartsNew    = 0;
  pnpStatsPartsDnp    = 0;
  pnpStatsPartsError  = 0;


  //Walk trough all elements for the board
  board(B) {
    pnpBasefile = B.name;

    B.elements(E) {
      int isSmd = 0;
      int isBottom = 0;

      //Determine centroid offset of the element
      int xmax = -2147483648,
          xmin = 2147483647,
          ymax = xmax,
          ymin = xmin;	
      xmax = E.x;
      xmin = E.x;
      ymax = E.y;
      ymin = E.y;

      E.package.contacts(C) {
        if (C.smd && C.smd.layer == 1) {
          isSmd = 1;
        }
        if (C.smd && C.smd.layer == 16) {
          isSmd = 1;
          isBottom = 1;
        }

        //Find centroid of this component
        if (C.x > xmax) xmax = C.x;
        if (C.y > ymax) ymax = C.y;
        if (C.x < xmin) xmin = C.x;
        if (C.y < ymin) ymin = C.y;
      }

      if(!isSmd && E.mirror == 1){
        isBottom = 1;
      }

      //If the part is SMD, process it
      //if (isSmd) {
		    real xCenter = (xmin + xmax) / 2;
        real yCenter = (ymin + ymax) / 2;
		
        pnpName[pnpCount]       = E.value + '-' + E.package.name;
        pnpDesignator[pnpCount] = E.name;
        pnpX[pnpCount]          = xCenter;
        pnpY[pnpCount]          = yCenter;
        pnpAngle[pnpCount]      = E.angle;
        pnpPos[pnpCount]        = isBottom;
        pnpType[pnpCount]       = isSmd;

        pnpCount++;
      //}

      //Autodetect to board outline
      B.wires(W) {
        if(W.layer == 20) {
          if(W.arc) {
            setCoordinates(W.arc.x1, W.arc.y1);
            setCoordinates(W.arc.x2, W.arc.y2);
            
            int angle = W.arc.angle2 - W.arc.angle1;
            
            int set_elements = round(angle/90);
            int start_element = round(W.arc.angle1/90);
            start_element = start_element % 4;
            
            for(int i = start_element; i < (start_element + set_elements); i++) {
              if(i == 0) {
                setCoordinates(W.arc.xc - W.arc.radius, W.arc.y1);
              } else if(i == 1) {
                setCoordinates(W.arc.x2, W.arc.yc + W.arc.radius);
              } else if(i == 2) {
                setCoordinates(W.arc.xc + W.arc.radius, W.arc.y1);
              } else if(i == 3) {
                setCoordinates(W.arc.x2, W.arc.yc - W.arc.radius);
              }
            }
          } else {
            setCoordinates(W.x1, W.y1);
            setCoordinates(W.x2, W.y2);
          }
        }
      }

      B.circles(C) {
        if(C.layer == 20) {
          setCoordinates(C.x + C.radius, C.y + C.radius);
          setCoordinates(C.x - C.radius, C.y - C.radius);
        }
      }
    } 
  }
}

if (!board) {
  dlgMessageBox(":\n    Start this ULP in a Board    \n");
  exit (0);  
} else {
  useAutomaticOffset  = strtol(argv[4]);
  flip                = strtol(argv[5]); 
  offsetX             = strtod(argv[6]); 
  offsetY             = strtod(argv[7]);

  loadBoardInformation();
  writeOutputFile(argv[1], strtol(argv[2]), strtol(argv[3]));
}
