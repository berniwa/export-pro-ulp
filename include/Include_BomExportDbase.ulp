/**
 * This ULP generates a dbase database from the BOM
 *
 * @author 		Bernhard Wörndl-Aichriedler <bwa@xdevelop.at>
 * @copyright	2009-2019, Bernhard Wörndl-Aichriedler
 * @license 	BSD-3-Clause
 */

string BOM_DBASE_COLUMNS[] = {"Stueckzahl", "Kurzb.", "Wert", "Bauform", "Refkennz.", "Lieferant", "Best. Nr.", "Hersteller", "Hs. Kennz.", "Barcode", "Preis/Stk.", "Reserv. 1", "Reserv. 2"};
int BOM_DBASE_COLUMN_WIDTH = 250;
string dbaseLine[];

string bomDatabaseSafe(string str)
{
	str = stringReplace(str, "µ", "u");
	return str;	
}

void bomDatabaseGetLine(int i)
{
	int k = 0;
	sprintf(dbaseLine[0], "%d", bomInfoPartCount[i]);
	for(int l = 0; l < BOM_DATA_COUNT; l++)
	{
		if(BOM_DATA_PART_ID[l] == bomInfoPartId[i])
		dbaseLine[1] = BOM_DATA_NAME[l];
	}
	
	dbaseLine[2] = bomDatabaseSafe(bomInfoValue[i]);
	dbaseLine[3] = bomDatabaseSafe(bomOutputNote[i]);
	dbaseLine[4] = bomDatabaseSafe(bomOutputParts[i]); 
	dbaseLine[5] = bomAttributeDistributor[i]; 
	dbaseLine[6] = bomAttributeOrderNo[i];
	dbaseLine[7] = bomAttributeManufacturer[i]; 
	dbaseLine[8] = bomAttributePartNo[i];
	dbaseLine[9] = bomAttributeReferenceNo[i]; 
	dbaseLine[10] = "";
	dbaseLine[11] = bomOutputGP1[i]; 
	dbaseLine[12] = bomOutputGP2[i];
}

void bomOutputDatabaseFile(string ofilename)
{
	output(ofilename, "wb")
	{
       		printf("%c%c%c%c", 0x03, 0x56, 0x0B, 0x1B);


    		int l, m, i, j, recs;


		l = bomInfoCount;
    		printf("%c%c%c%c", l & 0xFF, (l & 0xFF00) >> 8, (l & 0xFF0000) >> 16, (l & 0xFF000000) >> 24);

		//Länge des Header: 32 + (32*Datenfelder) + 1  
    		for (l = 0; BOM_DBASE_COLUMNS[l]; l++);
    		recs = l;
    		m = (l*32)+33;
    		printf("%c%c", m & 0xFF, (m & 0xFF00) >> 8);

    		m = (l*BOM_DBASE_COLUMN_WIDTH)+1;
    		printf("%c%c", m & 0xFF, (m & 0xFF00) >> 8);

    		printf("%c%c%c%c%c%c%c%c%c%c%c%c%c%c%c%c%c%c%c%c", 0x00, 0x00, 0x00, 0x00, 0x00, 0x00, 0x00, 0x00, 0x00, 0x00, 0x00, 0x00, 0x00, 0x00, 0x00, 0x00, 0x00, 0x00, 0x00, 0x00);

    		for (l = 0; BOM_DBASE_COLUMNS[l]; l++)
		{
			int ended = 0;
			for(int i = 0; i < 11; i++)
			{
				if(!ended && BOM_DBASE_COLUMNS[l][i] != 0)
				{
					if(BOM_DBASE_COLUMNS[l][i] == ' ')
					{
						printf("%c", '_');	
					}
					else
					{
						printf("%c", toupper(BOM_DBASE_COLUMNS[l][i]));	
					}					
				}
				else
				{
					ended = 1;
					printf("%c", 0x00);
				}
			}

			/*
    			if(strlen(BOM_DBASE_COLUMNS[l]) == 11){printf("Descriptio%c", 0x00);}
    			else
			{
				if(strlen(BOM_DBASE_COLUMNS[l]) < 11)
    		          	{
					printf("%s", BOM_DBASE_COLUMNS[l]);
				}
			}
			for(i = 0; i < (11 - strlen(BOM_DBASE_COLUMNS[l])); i++)
			{
				printf("%c", 0x00);
			}
			*/
			printf("%c%c%c%c%c%c", 0x43, 0x00, 0x00, 0x00, 0x00, BOM_DBASE_COLUMN_WIDTH);
			printf("%c%c%c%c%c%c%c%c%c%c%c%c%c%c%c", 0x05, 0x00, 0x00, 0x00, 0x00, 0x00, 0x00, 0x00, 0x00, 0x00, 0x00, 0x00, 0x00, 0x00, 0x00);
    		}
		printf("%c", 0x0D);

		int n;
		int numHeaders;
		string List;
  
  		for (l = 0;l < bomInfoCount; l++) 
		{
			printf("%c", 0x20);

			bomDatabaseGetLine(l);

    			for (i = 0; BOM_DBASE_COLUMNS[i]; i++) 
			{
          			printf("%-*s", BOM_DBASE_COLUMN_WIDTH, dbaseLine[i]);
      			}
		}

		printf("%c", 0x1a);
	}	
}
