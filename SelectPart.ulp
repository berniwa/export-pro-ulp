/**
 * Allows proper BOM management for EAGLE
 *
 * @author 		Bernhard Wörndl-Aichriedler <bwa@xdevelop.at>
 * @author 		Patricia Schöndorfer <ps@xdevelop.at>
 * @author 		Tobias Hofer <thofer@xdevelop.at>
 * @copyright	2016-2019, Bernhard Wörndl-Aichriedler
 * @license 	BSD-3-Clause
 */

 #usage "<b>Allows proper BOM management</b>\n"
       "<author>Bernhard Wörndl-Aichriedler 2006-2019 </author>"

#include "include/Include_Misc.ulp"
#include "include/Include_FastExecute.ulp"
#include "include/Include_BomConfig.ulp"
#include "include/Include_String.ulp"
#include "include/Include_BomCategory.ulp"
#include "include/Include_BomCommon.ulp"
#include "include/Include_BomPricing.ulp"
#include "include/Include_Language.ulp"
#include "include/Include_Si.ulp"
#include "include/Include_Config.ulp";

string stdDistributor = "xdevelop";

int rerun = 1, save = 1;

//GUI variables
string 	list[];
string partsWithOrderNo 	= "";
string partsWithPrice 		= "";
string availableParts 		= "";
string priceInformatiom 	= "";


char prefix[] = {'R', 'k', 'M', 'G', 'T'};

void debug(string msg, real val){
	sprintf(msg,"%s%f",msg,val);
	dlgMessageBox(msg);
}

string getTolerance(int select){
	string tol="";

	if(category[select]==0){
		if(strchr(values[select],'%')==-1){
			tol = cfg_defaultTolerance;
		}
		else{
			tol = strsub(values[select],(strchr(values[select],' ')+1));
		}
	}	
	return tol;
}

string getVoltage(int select){
	int tmp = strchr(values[select],'/');

	if(tmp>=0){
		return strsub(values[select],(tmp+1));
	}
	else {
		return cfg_defaultVoltage;
	}
	
}

string getOrderNo(int select){
	if(category[select]!=0&&category[select]!=2){
		return "";
	}

	string orderNo = "GP";

	if (category[select]==0){
		orderNo+="R";
	}
	else if(category[select]==2){
		orderNo+="C";
	}

	int l=0, a=0;
	for (int i = 0; i < strlen(packages[select]); i++){
		if(isdigit(packages[select][i])){
			l++;
			if(l>=4){
				break;
			}
		}
		else{
			l=0;
			a=i+1;
		}
	}
	orderNo+=strsub(packages[select],a,l);

	real val;
	val=siParseValue(values[select]);
	if (category[select]==0){
		val*=10;

		string tmp = "";
		sprintf(tmp,"%d",int(val));
		val=(((strlen(tmp)+1)%3)+1);

		orderNo+=strsub(tmp,0,int(val))+prefix[(strlen(tmp)-2)/3];

		tmp=strsub(tmp,int(val),(strchr(tmp,'0')-int(val)));

		if(strtod(tmp)==0){
			tmp="";
		}

		orderNo+=tmp;
	}
	else if(category[select]==2){
		val*=pow(10,12); //to get value in pF

		string tmp = "";
		sprintf(tmp,"%d",int(val));

		val=strlen(tmp)-2;
		tmp=strsub(tmp,0,2);

		sprintf(orderNo,"%s%s%d",orderNo,tmp,int(val));
	}

	string v=getVoltage(select);

	if(v!="50V"){
		orderNo+="-"+strsub(v,0,strlen(v)-1);
	}

	return orderNo;
}



real calculatePrice(){
	real mprice = 0;

	for(int i = 0; i < partcount; i++){
		mprice += strtod(price[i]);
	}
	return mprice;
}

real calculatePriceWOUnpopulated(){
	real mprice = 0;

	for(int i = 0; i < partcount; i++){
		if(populate[i] != "DNP"){
			mprice += strtod(price[i]);
		}
	}
	return mprice;
}

int calculateAvailableParts(){
	int mpartcount = 0;

	for(int i = 0; i < partcount; i++){
		int av = strtod(available[i]);
		if(av > bomCountPartsWithSameOrderNo(distributor[i], order_no[i])){mpartcount++;}
	}
	return mpartcount;	
}

int calculatePartsWithOrderNo(){
	int mpartcount = 0;

	for(int i = 0; i < partcount; i++){
		if(distributor[i] != "" && order_no[i] != ""){
			mpartcount++;
		}
	}
	return mpartcount;	
}

int calculatePartsWithPrice(){
	int mpartcount = 0;

	for(int i = 0; i < partcount; i++){
		if(price[i] != ""){mpartcount++;}
	}
	return mpartcount;	
}

void requestAllPrices(){
	bomPricingRequestAll();
}

void updateAttributeList(){
	for(int i = 0; i < partcount; i++){
		sprintf(list[i], "%s\t%s\t%s\t%d\t%s\t%s\t%s\t%s\t%s\t%s\t%s\t%s\t%s\t%s\t%s\t%s\t%s\t%s\t%s", 
			names[i], values[i], packages[i] , pages[i], 
			distributor[i], order_no[i], 
			manufacturer[i], part_no[i],
			price[i], available[i], per_pkg[i], min_qty[i], qty_mul[i], 
			populate[i], BOM_PART_CATEGORIES[category[i]], note[i],
			minTemp[i], maxTemp[i], rohs[i]
		);	
	}
		
	sprintf(partsWithOrderNo, 	"%d %s %d", calculatePartsWithOrderNo(), lanGetText("general.of"), partcount);
	sprintf(partsWithPrice, 	"%d %s %d", calculatePartsWithPrice(), lanGetText("general.of"), partcount);
	sprintf(availableParts, 	"%d %s %d", calculateAvailableParts(), lanGetText("general.of"), partcount);
	sprintf(priceInformatiom, 	"%.3f (%.3f) Euro", calculatePriceWOUnpopulated(), calculatePrice());
}

int getPopulateMode(string populate){
	int populateMode = 0;

	if(populate == ""){
		populateMode = 0;
	} 
	else if(populate == "DNP"){
		populateMode = 1;
	} 	
	else{
		populateMode = 2;
	}	
	return populateMode;
}


string getPopulate(int populateMode, string populate)
{
	if(populateMode == 0){
		populate = "";
	} 
	else if(populateMode == 1){
		populate = "DNP";
	} 
	return populate;
}


void editDevice(int selected){
	int saveDevice = 1;
	int mode = 1;
	int populateMode = 0;
	int noteMode = 0;

	populateMode = getPopulateMode(populate[selected]);

	//Note modes
	noteMode = -1;
	int i = 0;
	for(i = 0; BOM_PREDEFINED_NOTES[i]; i++){
		if(note[selected] == BOM_PREDEFINED_NOTES[i]){
			noteMode = i;
		}
	}
	if(noteMode == -1){
		noteMode = i;
	}

	dlgDialog(lanGetText("headline.dlg.editDevice")){		
		dlgGroup(lanGetText("headline.DevInfo")){
			dlgHBoxLayout{
				dlgLabel(lanGetText("tab.part")+":");
				dlgLabel(names[selected]);	
				dlgLabel(lanGetText("tab.value")+":");
				dlgLabel(values[selected]);
				dlgLabel(lanGetText("tab.pac")+":");	
				dlgLabel(packages[selected]);
			}
		}

		dlgGroup(lanGetText("headline.populate")){
			dlgHBoxLayout{
				dlgLabel(lanGetText("tab.populate"));
				dlgRadioButton(lanGetText("general.yes"), 	populateMode);
				dlgRadioButton(lanGetText("general.no"), 	populateMode);
				dlgRadioButton(lanGetText("general.special")+":", 	populateMode);
				dlgStringEdit(populate[selected]);	
			}			
		}

		dlgGroup(lanGetText("headline.updatemode")){
			dlgHBoxLayout{
 				dlgRadioButton(lanGetText("tab.part")+" "+lanGetText("general.name"), mode);
  				dlgRadioButton(lanGetText("tab.value")+" && "+lanGetText("tab.pac"), mode);
  				dlgRadioButton(lanGetText("tab.value"), mode);
  				dlgRadioButton(lanGetText("tab.pac"), mode);
			}			
		}

		dlgGroup(lanGetText("tab.note")){
			dlgVBoxLayout{
				for(i = 0; BOM_PREDEFINED_NOTES[i]; i++){
					dlgRadioButton(BOM_PREDEFINED_NOTES[i], noteMode);
				}
				dlgHBoxLayout{
					dlgRadioButton(lanGetText("general.custom")+":", noteMode);
					dlgStringEdit(note[selected]);						
				}
			}			
		}

		if (category[selected]==0||category[selected]==2){
			string orderNr = "";
			string volt = "";
			string tol = "";

			tol = getTolerance(selected);
			volt = getVoltage(selected);
			orderNr=getOrderNo(selected);


			dlgGroup(lanGetText("headline.AutoDetect")){
				dlgVBoxLayout{
					dlgGridLayout{
						dlgCell(0, 0) dlgLabel(lanGetText("tab.value")+":");
						dlgCell(0, 1) dlgLabel(values[selected]);
						dlgCell(0, 2) dlgLabel(lanGetText("general.voltage")+":");
						dlgCell(0, 3) dlgLabel(volt);
						dlgCell(1, 0) dlgLabel(lanGetText("tab.distriputor")+":");
						dlgCell(1, 1) dlgLabel(stdDistributor);
						dlgCell(1, 2) dlgLabel(lanGetText("tab.order.No")+":");
						dlgCell(1, 3) dlgLabel(orderNr);
					}
					dlgHBoxLayout{
						dlgStretch(1);
						dlgPushButton(lanGetText("button.apply")){
							distributor[selected]=stdDistributor;
							order_no[selected]=orderNr;
							manufacturer[selected]="any";

							//If the voltage is the default voltage, it is already in the value
							part_no[selected]=strsub(values[selected],0,strchr(values[selected],' '));
							if(volt == cfg_defaultVoltage){
								part_no[selected] += "/" + volt;
							}
							if(tol == cfg_defaultTolerance){
								part_no[selected] += "/" + tol;
							}
							bomPricingRequest(selected);
						}
					}
					
				}
			}
		}

		dlgGroup(lanGetText("headline.newValues")){		
			dlgGridLayout{
				dlgCell(0, 0) dlgLabel(lanGetText("tab.distriputor"));
				dlgCell(0, 1) dlgStringEdit(distributor[selected]);
				dlgCell(0, 2) dlgLabel(lanGetText("tab.order.No"));
				dlgCell(0, 3) dlgStringEdit(order_no[selected]);	
				dlgCell(1, 0) dlgLabel(lanGetText("tab.manufacturer"));
				dlgCell(1, 1) dlgStringEdit(manufacturer[selected]);	
				dlgCell(1, 2) dlgLabel(lanGetText("tab.part.No"));
				dlgCell(1, 3) dlgStringEdit(part_no[selected]);	
				dlgCell(2, 0) dlgLabel(lanGetText("tab.price")+"*");
				dlgCell(2, 1) dlgStringEdit(price[selected]);	
				dlgCell(2, 2) dlgLabel(lanGetText("settings.newVal.prices")+"*");
				dlgCell(2, 3) dlgStringEdit(prices[selected]);
				dlgCell(3, 0) dlgLabel(lanGetText("settings.newVal.minQuantity")+"*");
				dlgCell(3, 1) dlgStringEdit(min_qty[selected]);	
				dlgCell(3, 2) dlgLabel(lanGetText("settings.newVal.QuantityMulti")+"*");
				dlgCell(3, 3) dlgStringEdit(qty_mul[selected]);
				dlgCell(4, 0) dlgLabel(lanGetText("settings.newVal.available")+"*");
				dlgCell(4, 1) dlgStringEdit(available[selected]);	
				dlgCell(4, 2) dlgLabel(lanGetText("settings.newVal.perPkg")+"*");
				dlgCell(4, 3) dlgStringEdit(per_pkg[selected]);
				dlgCell(5, 0) dlgLabel(lanGetText("settings.newVal.datasheet")+"*");
				dlgCell(5, 1) dlgStringEdit(datasheet[selected]);
				dlgCell(5, 2) dlgLabel(lanGetText("tab.category"));
				dlgCell(5, 3) dlgComboBox(BOM_PART_CATEGORIES, category[selected]);
				dlgCell(6, 0) dlgLabel(lanGetText("tab.minTemp")+"*");
				dlgCell(6, 1) dlgStringEdit(minTemp[selected]);	
				dlgCell(6, 2) dlgLabel(lanGetText("tab.maxTemp")+"*");
				dlgCell(6, 3) dlgStringEdit(maxTemp[selected]);
				dlgCell(7, 0) dlgLabel(lanGetText("tab.rohs")+"*");
				dlgCell(7, 1) dlgStringEdit(rohs[selected]);	
				dlgCell(8, 0, 8, 2) dlgLabel(lanGetText("dlg.newVal.footnote"));	
				dlgCell(8, 3, 8, 3) dlgPushButton(lanGetText("button.request")) { 
					bomPricingRequest(selected); 
				} 	
			}
		}

		dlgHBoxLayout{	
			dlgStretch(1);
			dlgPushButton(lanGetText("button.cancel")){dlgReject();}
			dlgPushButton(lanGetText("button.save")){dlgAccept(); }
		}
	};

	if(saveDevice){

		if(populateMode == 0){
			populate[selected] = "";
		} 
		else if(populateMode == 1){
			populate[selected] = "DNP";
		} 

		if(BOM_PREDEFINED_NOTES[noteMode]){
			note[selected] = BOM_PREDEFINED_NOTES[noteMode];
		}

		bomUpdatePart(selected, mode);
	}	
}

int showListOfDevices(char singelPart){

	if(board){
		exit("EDIT .sch; RUN '"+argv[0]+"';");
	}

	int selected = 0;
	int sorted = 0;
	int quantity = 1;
	string populateset = "DNP"; 
	int populateMode = 0;


	loadConfig();
	
	bomLoadData();
	lanLoadText(cfg_textLanguage);

	while(1){
		updateAttributeList();
	
		if(!singelPart){
			int dstatus = dlgDialog(lanGetText("headline.dlg.SPMain")){
				dlgHBoxLayout{
					dlgVBoxLayout dlgSpacing(600);
					dlgListView(lanGetText("tab.part")+"\t"+
						lanGetText("tab.value")+"\t"+
						lanGetText("tab.pac")+"\t"+
						lanGetText("tab.sheet")+"\t"+
						lanGetText("tab.distriputor")+"\t"+
						lanGetText("tab.order.No")+"\t"+
						lanGetText("tab.manufacturer")+"\t"+
						lanGetText("tab.part.No")+"\t"+
						lanGetText("tab.price")+"\t"+
						lanGetText("tab.available")+"\t"+
						lanGetText("tab.perPkg")+"\t"+
						lanGetText("tab.minQuantity")+"\t"+
						lanGetText("tab.QuantityMulti")+"\t"+
						lanGetText("tab.populate")+"\t"+
						lanGetText("tab.category")+"\t"+
						lanGetText("tab.note")+"\t"+
						lanGetText("tab.minTemp")+"\t"+
						lanGetText("tab.maxTemp")+"\t"+
						lanGetText("tab.rohs"), 
						list, selected, sorted)
					{
						if (dlgSelectionChanged()){
							populateset 	= populate[selected];
							populateMode 	= getPopulateMode(populate[selected]);
						} else{
							editDevice(selected);
							updateAttributeList();
						}
					}
				}
				dlgHBoxLayout{
					dlgVBoxLayout dlgSpacing(100);
					dlgGroup(lanGetText("general.info")){
						dlgGridLayout{
										
							dlgCell(0, 1) dlgLabel(lanGetText("settings.orderInfo")+":");
							dlgCell(0, 2) dlgLabel(partsWithOrderNo, 1);
							dlgCell(1, 1) dlgLabel(lanGetText("settings.priceInfo")+":");
							dlgCell(1, 2) dlgLabel(partsWithPrice, 1);
							dlgCell(2, 1) dlgLabel(lanGetText("settings.available")+":");
							dlgCell(2, 2) dlgLabel(availableParts, 1);
						}
					}
					dlgGroup(lanGetText("headline.pricing")){
						dlgGridLayout{
							dlgCell(0, 3) dlgLabel(lanGetText("settings.quanttity")+":");
							dlgCell(0, 4) dlgIntEdit(quantity);
							dlgCell(1, 3, 1, 4) dlgPushButton(lanGetText("button.priceRequest")){
								bomPricingRequestAllWithMultiplier(quantity);
								updateAttributeList();
							};
							dlgCell(2, 3) dlgLabel(lanGetText("settings.overPrice")+"*:");
							dlgCell(2, 4) dlgLabel(priceInformatiom, 1);
						}
					}	
					dlgGroup(lanGetText("headline.populate")){
						dlgGridLayout{
							dlgCell(0, 0) dlgLabel(lanGetText("tab.populate"));
							dlgCell(0, 1) dlgRadioButton(lanGetText("general.yes"), 			populateMode);
							dlgCell(1, 1) dlgRadioButton(lanGetText("general.no"), 				populateMode);
							dlgCell(2, 1) dlgRadioButton(lanGetText("general.special")+":", 	populateMode);

							dlgCell(2, 2) dlgStringEdit(populateset);	
							dlgCell(3, 0, 3, 2) dlgPushButton(lanGetText("button.setpopulate")){
								populate[selected] = getPopulate(populateMode, populateset);
								updateAttributeList();
							};
						}			
					}			
					dlgStretch(1);
					dlgVBoxLayout{
						dlgStretch(1); 
						dlgPushButton("⚙") {
							if(editUserConfig()){
								exit("RUN '" + argv[0] + "';");
							}
						};
						dlgPushButton(lanGetText("button.cancel")){dlgReject(); return 0;}
						dlgPushButton(lanGetText("button.save")){dlgAccept(); return 1;}
					}
				}
			};
			if(dstatus == -1){
				break;
			}
		}
		else{
			string iname;
			schematic(S){
				S.allparts(P){
					P.instances(I){
						if(ingroup(I)) {
							iname=I.name;
						}
					}
				}
			}
			string pVal[];
			for(int n=0;n<partcount;n++){
				strsplit(pVal,list[n],'\t');

				if(strstr(pVal[0],iname)!=-1){
					selected=n;
					break;
				}
			}

			editDevice(selected);
			updateAttributeList();
			return 1;
		}

	}

	return 1;
}

if(showListOfDevices(strtol(argv[1]))){
	executeAndExit(bomUpdateChanges());
}
